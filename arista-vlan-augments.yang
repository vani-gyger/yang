module "arista-vlan-augments" {
	namespace "http://arista.com/yang/openconfig/network-instance/vlan/augments";
	prefix "arista-vlan-augments";
	import "openconfig-network-instance" {
		prefix "oc-netinst";
	}
	import "openconfig-extensions" {
		prefix "oc-ext";
	}
	organization "Arista Networks <http://arista.com/>";
	contact "Arista Networks, Inc.
	         Product Support";
	description "This module contains OpenConfig vlan augments in Arista EOS.
	             
	             Copyright (c) 2017 Arista Networks, Inc. All rights reserved.";
	oc-ext:openconfig-version "1.1.2";
	revision "2020-11-30" {
		description "Fix errors reported by pyang.";
		reference "1.1.2";
	}
	revision "2020-01-06" {
		description "Removed unused imports.";
		reference "1.1.1";
	}
	revision "2019-11-18" {
		description "Removed unneeded EVPN augments.";
		reference "1.1.0";
	}
	revision "2017-10-01" {
		description "Initial augment file.";
		reference "1.0.0";
	}
	grouping "vlanAddionalEOSConfig" {
		leaf "mac-learning" {
			type "boolean";
			default "true";
			description "Turn on/off mac learning on this VLAN.";
		}
		leaf-list "trunk-groups" {
			type "string";
			description "Set of trunk groups for this vlan. A vlan that is a member of a trunk group is only allowed out ports that are also members of that trunk group.";
		}
		description "Grouping of additional EOS VLAN configuration.";
	}
	augment "/oc-netinst:network-instances/oc-netinst:network-instance/oc-netinst:vlans/oc-netinst:vlan/oc-netinst:config" {
		uses "vlanAddionalEOSConfig";
		description "Add additional parameters to VLAN configuration.";
	}
	augment "/oc-netinst:network-instances/oc-netinst:network-instance/oc-netinst:vlans/oc-netinst:vlan/oc-netinst:state" {
		uses "vlanAddionalEOSConfig";
		description "Add additional parameters to VLAN state.";
	}
}
