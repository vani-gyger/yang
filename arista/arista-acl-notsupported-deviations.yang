module "arista-acl-notsupported-deviations" {
	namespace "http://arista.com/yang/openconfig/acl/notsupported-deviations";
	prefix "arista-acl-notsupported-deviations";
	import "openconfig-acl" {
		prefix "oc-acl";
	}
	organization "Arista Networks, Inc.";
	contact "Arista Networks, Inc.
	         Product Support";
	description "This module contains OpenConfig acl deviations in Arista EOS.
	             Copyright (c) 2020 Arista Networks, Inc. All rights reserved.";
	revision "2024-10-02" {
		description "Auto-generated not-supported deviations for unsupported paths";
	}
	deviation "/oc-acl:acl/oc-acl:config" {
		description "Not-supported deviation.";
		deviate "not-supported";
	}
	deviation "/oc-acl:acl/oc-acl:acl-sets/oc-acl:acl-set/oc-acl:acl-entries/oc-acl:acl-entry/oc-acl:mpls" {
		description "Not-supported deviation.";
		deviate "not-supported";
	}
	deviation "/oc-acl:acl/oc-acl:acl-sets/oc-acl:acl-set/oc-acl:acl-entries/oc-acl:acl-entry/oc-acl:ipv4/oc-acl:icmpv4" {
		description "Not-supported deviation.";
		deviate "not-supported";
	}
	deviation "/oc-acl:acl/oc-acl:acl-sets/oc-acl:acl-set/oc-acl:acl-entries/oc-acl:acl-entry/oc-acl:ipv4/oc-acl:config/oc-acl:destination-address-prefix-set" {
		description "Not-supported deviation.";
		deviate "not-supported";
	}
	deviation "/oc-acl:acl/oc-acl:acl-sets/oc-acl:acl-set/oc-acl:acl-entries/oc-acl:acl-entry/oc-acl:ipv4/oc-acl:config/oc-acl:dscp-set" {
		description "Not-supported deviation.";
		deviate "not-supported";
	}
	deviation "/oc-acl:acl/oc-acl:acl-sets/oc-acl:acl-set/oc-acl:acl-entries/oc-acl:acl-entry/oc-acl:ipv4/oc-acl:config/oc-acl:length" {
		description "Not-supported deviation.";
		deviate "not-supported";
	}
	deviation "/oc-acl:acl/oc-acl:acl-sets/oc-acl:acl-set/oc-acl:acl-entries/oc-acl:acl-entry/oc-acl:ipv4/oc-acl:config/oc-acl:source-address-prefix-set" {
		description "Not-supported deviation.";
		deviate "not-supported";
	}
	deviation "/oc-acl:acl/oc-acl:acl-sets/oc-acl:acl-set/oc-acl:acl-entries/oc-acl:acl-entry/oc-acl:ipv4/oc-acl:state/oc-acl:destination-address-prefix-set" {
		description "Not-supported deviation.";
		deviate "not-supported";
	}
	deviation "/oc-acl:acl/oc-acl:acl-sets/oc-acl:acl-set/oc-acl:acl-entries/oc-acl:acl-entry/oc-acl:ipv4/oc-acl:state/oc-acl:dscp-set" {
		description "Not-supported deviation.";
		deviate "not-supported";
	}
	deviation "/oc-acl:acl/oc-acl:acl-sets/oc-acl:acl-set/oc-acl:acl-entries/oc-acl:acl-entry/oc-acl:ipv4/oc-acl:state/oc-acl:length" {
		description "Not-supported deviation.";
		deviate "not-supported";
	}
	deviation "/oc-acl:acl/oc-acl:acl-sets/oc-acl:acl-set/oc-acl:acl-entries/oc-acl:acl-entry/oc-acl:ipv4/oc-acl:state/oc-acl:source-address-prefix-set" {
		description "Not-supported deviation.";
		deviate "not-supported";
	}
	deviation "/oc-acl:acl/oc-acl:acl-sets/oc-acl:acl-set/oc-acl:acl-entries/oc-acl:acl-entry/oc-acl:ipv6/oc-acl:icmpv6" {
		description "Not-supported deviation.";
		deviate "not-supported";
	}
	deviation "/oc-acl:acl/oc-acl:acl-sets/oc-acl:acl-set/oc-acl:acl-entries/oc-acl:acl-entry/oc-acl:ipv6/oc-acl:config/oc-acl:destination-address-prefix-set" {
		description "Not-supported deviation.";
		deviate "not-supported";
	}
	deviation "/oc-acl:acl/oc-acl:acl-sets/oc-acl:acl-set/oc-acl:acl-entries/oc-acl:acl-entry/oc-acl:ipv6/oc-acl:config/oc-acl:dscp-set" {
		description "Not-supported deviation.";
		deviate "not-supported";
	}
	deviation "/oc-acl:acl/oc-acl:acl-sets/oc-acl:acl-set/oc-acl:acl-entries/oc-acl:acl-entry/oc-acl:ipv6/oc-acl:config/oc-acl:length" {
		description "Not-supported deviation.";
		deviate "not-supported";
	}
	deviation "/oc-acl:acl/oc-acl:acl-sets/oc-acl:acl-set/oc-acl:acl-entries/oc-acl:acl-entry/oc-acl:ipv6/oc-acl:config/oc-acl:source-address-prefix-set" {
		description "Not-supported deviation.";
		deviate "not-supported";
	}
	deviation "/oc-acl:acl/oc-acl:acl-sets/oc-acl:acl-set/oc-acl:acl-entries/oc-acl:acl-entry/oc-acl:ipv6/oc-acl:state/oc-acl:destination-address-prefix-set" {
		description "Not-supported deviation.";
		deviate "not-supported";
	}
	deviation "/oc-acl:acl/oc-acl:acl-sets/oc-acl:acl-set/oc-acl:acl-entries/oc-acl:acl-entry/oc-acl:ipv6/oc-acl:state/oc-acl:dscp-set" {
		description "Not-supported deviation.";
		deviate "not-supported";
	}
	deviation "/oc-acl:acl/oc-acl:acl-sets/oc-acl:acl-set/oc-acl:acl-entries/oc-acl:acl-entry/oc-acl:ipv6/oc-acl:state/oc-acl:length" {
		description "Not-supported deviation.";
		deviate "not-supported";
	}
	deviation "/oc-acl:acl/oc-acl:acl-sets/oc-acl:acl-set/oc-acl:acl-entries/oc-acl:acl-entry/oc-acl:ipv6/oc-acl:state/oc-acl:source-address-prefix-set" {
		description "Not-supported deviation.";
		deviate "not-supported";
	}
	deviation "/oc-acl:acl/oc-acl:acl-sets/oc-acl:acl-set/oc-acl:acl-entries/oc-acl:acl-entry/oc-acl:transport/oc-acl:config/oc-acl:builtin-detail" {
		description "Not-supported deviation.";
		deviate "not-supported";
	}
	deviation "/oc-acl:acl/oc-acl:acl-sets/oc-acl:acl-set/oc-acl:acl-entries/oc-acl:acl-entry/oc-acl:transport/oc-acl:config/oc-acl:destination-port-set" {
		description "Not-supported deviation.";
		deviate "not-supported";
	}
	deviation "/oc-acl:acl/oc-acl:acl-sets/oc-acl:acl-set/oc-acl:acl-entries/oc-acl:acl-entry/oc-acl:transport/oc-acl:config/oc-acl:detail-mode" {
		description "Not-supported deviation.";
		deviate "not-supported";
	}
	deviation "/oc-acl:acl/oc-acl:acl-sets/oc-acl:acl-set/oc-acl:acl-entries/oc-acl:acl-entry/oc-acl:transport/oc-acl:config/oc-acl:explicit-detail-match-mode" {
		description "Not-supported deviation.";
		deviate "not-supported";
	}
	deviation "/oc-acl:acl/oc-acl:acl-sets/oc-acl:acl-set/oc-acl:acl-entries/oc-acl:acl-entry/oc-acl:transport/oc-acl:config/oc-acl:source-port-set" {
		description "Not-supported deviation.";
		deviate "not-supported";
	}
	deviation "/oc-acl:acl/oc-acl:acl-sets/oc-acl:acl-set/oc-acl:acl-entries/oc-acl:acl-entry/oc-acl:transport/oc-acl:state/oc-acl:builtin-detail" {
		description "Not-supported deviation.";
		deviate "not-supported";
	}
	deviation "/oc-acl:acl/oc-acl:acl-sets/oc-acl:acl-set/oc-acl:acl-entries/oc-acl:acl-entry/oc-acl:transport/oc-acl:state/oc-acl:destination-port-set" {
		description "Not-supported deviation.";
		deviate "not-supported";
	}
	deviation "/oc-acl:acl/oc-acl:acl-sets/oc-acl:acl-set/oc-acl:acl-entries/oc-acl:acl-entry/oc-acl:transport/oc-acl:state/oc-acl:detail-mode" {
		description "Not-supported deviation.";
		deviate "not-supported";
	}
	deviation "/oc-acl:acl/oc-acl:acl-sets/oc-acl:acl-set/oc-acl:acl-entries/oc-acl:acl-entry/oc-acl:transport/oc-acl:state/oc-acl:explicit-detail-match-mode" {
		description "Not-supported deviation.";
		deviate "not-supported";
	}
	deviation "/oc-acl:acl/oc-acl:acl-sets/oc-acl:acl-set/oc-acl:acl-entries/oc-acl:acl-entry/oc-acl:transport/oc-acl:state/oc-acl:source-port-set" {
		description "Not-supported deviation.";
		deviate "not-supported";
	}
}
