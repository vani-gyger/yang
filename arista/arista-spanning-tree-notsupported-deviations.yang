module "arista-spanning-tree-notsupported-deviations" {
	namespace "http://arista.com/yang/openconfig/spanning-tree/notsupported-deviations";
	prefix "arista-spanning-tree-notsupported-deviations";
	import "openconfig-spanning-tree" {
		prefix "oc-stp";
	}
	organization "Arista Networks, Inc.";
	contact "Arista Networks, Inc.
	         Product Support";
	description "This module contains OpenConfig spanning-tree deviations in Arista EOS.
	             Copyright (c) 2020 Arista Networks, Inc. All rights reserved.";
	revision "2024-10-02" {
		description "Auto-generated not-supported deviations for unsupported paths";
	}
	deviation "/oc-stp:stp/oc-stp:interfaces" {
		description "Not-supported deviation.";
		deviate "not-supported";
	}
	deviation "/oc-stp:stp/oc-stp:mstp" {
		description "Not-supported deviation.";
		deviate "not-supported";
	}
	deviation "/oc-stp:stp/oc-stp:rapid-pvst" {
		description "Not-supported deviation.";
		deviate "not-supported";
	}
	deviation "/oc-stp:stp/oc-stp:rstp" {
		description "Not-supported deviation.";
		deviate "not-supported";
	}
	deviation "/oc-stp:stp/oc-stp:global/oc-stp:config/oc-stp:bpdu-filter" {
		description "Not-supported deviation.";
		deviate "not-supported";
	}
	deviation "/oc-stp:stp/oc-stp:global/oc-stp:config/oc-stp:bpdu-guard" {
		description "Not-supported deviation.";
		deviate "not-supported";
	}
	deviation "/oc-stp:stp/oc-stp:global/oc-stp:config/oc-stp:bpduguard-timeout-recovery" {
		description "Not-supported deviation.";
		deviate "not-supported";
	}
	deviation "/oc-stp:stp/oc-stp:global/oc-stp:config/oc-stp:bridge-assurance" {
		description "Not-supported deviation.";
		deviate "not-supported";
	}
	deviation "/oc-stp:stp/oc-stp:global/oc-stp:config/oc-stp:enabled-protocol" {
		description "Not-supported deviation.";
		deviate "not-supported";
	}
	deviation "/oc-stp:stp/oc-stp:global/oc-stp:config/oc-stp:etherchannel-misconfig-guard" {
		description "Not-supported deviation.";
		deviate "not-supported";
	}
	deviation "/oc-stp:stp/oc-stp:global/oc-stp:config/oc-stp:loop-guard" {
		description "Not-supported deviation.";
		deviate "not-supported";
	}
	deviation "/oc-stp:stp/oc-stp:global/oc-stp:state/oc-stp:bpdu-filter" {
		description "Not-supported deviation.";
		deviate "not-supported";
	}
	deviation "/oc-stp:stp/oc-stp:global/oc-stp:state/oc-stp:bpdu-guard" {
		description "Not-supported deviation.";
		deviate "not-supported";
	}
	deviation "/oc-stp:stp/oc-stp:global/oc-stp:state/oc-stp:bpduguard-timeout-recovery" {
		description "Not-supported deviation.";
		deviate "not-supported";
	}
	deviation "/oc-stp:stp/oc-stp:global/oc-stp:state/oc-stp:bridge-assurance" {
		description "Not-supported deviation.";
		deviate "not-supported";
	}
	deviation "/oc-stp:stp/oc-stp:global/oc-stp:state/oc-stp:enabled-protocol" {
		description "Not-supported deviation.";
		deviate "not-supported";
	}
	deviation "/oc-stp:stp/oc-stp:global/oc-stp:state/oc-stp:etherchannel-misconfig-guard" {
		description "Not-supported deviation.";
		deviate "not-supported";
	}
	deviation "/oc-stp:stp/oc-stp:global/oc-stp:state/oc-stp:loop-guard" {
		description "Not-supported deviation.";
		deviate "not-supported";
	}
}
