module "arista-exp-eos-vxlan" {
	yang-version "1";
	namespace "http://arista.com/yang/experimental/eos/vxlan";
	prefix "vxlan-exp";
	import "openconfig-interfaces" {
		prefix "oc-if";
	}
	import "arista-exp-eos-vxlan-config" {
		prefix "vxlan-config-exp";
	}
	organization "Arista Networks <http://arista.com/>";
	contact "Arista Networks, Inc.
	         Product Support";
	description "This module contains OpenConfig VXLAN augments in Arista EOS.
	             
	             Copyright (c) 2018 Arista Networks, Inc. All rights reserved.";
	revision "2023-11-01" {
		description "Move lists outside of config containers.";
		reference "1.0.0";
	}
	revision "2023-03-03" {
		description "Remove the constraint that arista-vxlan is valid only for Vxlan1 interface.";
		reference "0.1.1";
	}
	revision "2018-08-01" {
		description "Initial revision";
		reference "0.1.0";
	}
	grouping "vxlan-top" {
		description "Top-level VXLAN config and state containers";
		container "arista-vxlan" {
			description "Container for VXLAN configuration
			             and state";
			container "config" {
				description "Configuration data for VXLAN interfaces";
				leaf "mac-learn-mode" {
					type "vxlan-config-exp:mac-learn-mode";
					description "MAC learning mode";
				}
				uses "vxlan-config-exp:vti-config";
			}
			container "state" {
				config "false";
				description "State data for VXLAN interfaces";
				leaf "mac-learn-mode" {
					type "vxlan-config-exp:mac-learn-mode";
					description "MAC learning mode";
				}
				uses "vxlan-config-exp:vti-config";
			}
			uses "vxlan-config-exp:flood-vtep-group";
			uses "vxlan-config-exp:vlan-flood-vtep-group";
			uses "vxlan-config-exp:mac-learn-mode-group";
			uses "vxlan-config-exp:vlan-mac-learn-mode-group";
			uses "vxlan-config-exp:vti-mcast-group";
			uses "vxlan-config-exp:vti-vrf-to-vnis";
			uses "vxlan-config-exp:vti-vlan-to-vnis";
		}
	}
	augment "/oc-if:interfaces/oc-if:interface" {
		description "Adds additional VXLAN-specific configuration to
		             interfaces model";
		uses "vxlan-top";
	}
}
