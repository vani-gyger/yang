module "arista-interfaces-notsupported-deviations" {
	namespace "http://arista.com/yang/openconfig/interfaces/notsupported-deviations";
	prefix "arista-interfaces-notsupported-deviations";
	import "openconfig-hercules-interfaces" {
		prefix "herc-if";
	}
	import "openconfig-if-aggregate" {
		prefix "oc-lag";
	}
	import "openconfig-if-ethernet" {
		prefix "oc-eth";
	}
	import "openconfig-if-ip" {
		prefix "oc-ip";
	}
	import "openconfig-if-tunnel" {
		prefix "oc-tun";
	}
	import "openconfig-interfaces" {
		prefix "oc-if";
	}
	import "openconfig-vlan" {
		prefix "oc-vlan";
	}
	organization "Arista Networks, Inc.";
	contact "Arista Networks, Inc.
	         Product Support";
	description "This module contains OpenConfig interfaces deviations in Arista EOS.
	             Copyright (c) 2020 Arista Networks, Inc. All rights reserved.";
	revision "2024-10-02" {
		description "Auto-generated not-supported deviations for unsupported paths";
	}
	deviation "/oc-if:interfaces/oc-if:interface/oc-if:penalty-based-aied" {
		description "Not-supported deviation.";
		deviate "not-supported";
	}
	deviation "/oc-if:interfaces/oc-if:interface/oc-eth:ethernet/oc-eth:config/oc-eth:fec-mode" {
		description "Not-supported deviation.";
		deviate "not-supported";
	}
	deviation "/oc-if:interfaces/oc-if:interface/oc-eth:ethernet/oc-eth:config/oc-eth:standalone-link-training" {
		description "Not-supported deviation.";
		deviate "not-supported";
	}
	deviation "/oc-if:interfaces/oc-if:interface/oc-eth:ethernet/oc-eth:state/herc-if:forwarding-viable" {
		description "Not-supported deviation.";
		deviate "not-supported";
	}
	deviation "/oc-if:interfaces/oc-if:interface/oc-eth:ethernet/oc-eth:state/oc-eth:fec-mode" {
		description "Not-supported deviation.";
		deviate "not-supported";
	}
	deviation "/oc-if:interfaces/oc-if:interface/oc-eth:ethernet/oc-eth:state/oc-eth:standalone-link-training" {
		description "Not-supported deviation.";
		deviate "not-supported";
	}
	deviation "/oc-if:interfaces/oc-if:interface/oc-eth:ethernet/oc-eth:state/oc-eth:counters/oc-eth:in-block-errors" {
		description "Not-supported deviation.";
		deviate "not-supported";
	}
	deviation "/oc-if:interfaces/oc-if:interface/oc-eth:ethernet/oc-eth:state/oc-eth:counters/oc-eth:in-carrier-errors" {
		description "Not-supported deviation.";
		deviate "not-supported";
	}
	deviation "/oc-if:interfaces/oc-if:interface/oc-eth:ethernet/oc-eth:state/oc-eth:counters/oc-eth:in-interrupted-tx" {
		description "Not-supported deviation.";
		deviate "not-supported";
	}
	deviation "/oc-if:interfaces/oc-if:interface/oc-eth:ethernet/oc-eth:state/oc-eth:counters/oc-eth:in-late-collision" {
		description "Not-supported deviation.";
		deviate "not-supported";
	}
	deviation "/oc-if:interfaces/oc-if:interface/oc-eth:ethernet/oc-eth:state/oc-eth:counters/oc-eth:in-mac-errors-rx" {
		description "Not-supported deviation.";
		deviate "not-supported";
	}
	deviation "/oc-if:interfaces/oc-if:interface/oc-eth:ethernet/oc-eth:state/oc-eth:counters/oc-eth:in-single-collision" {
		description "Not-supported deviation.";
		deviate "not-supported";
	}
	deviation "/oc-if:interfaces/oc-if:interface/oc-eth:ethernet/oc-eth:state/oc-eth:counters/oc-eth:in-symbol-error" {
		description "Not-supported deviation.";
		deviate "not-supported";
	}
	deviation "/oc-if:interfaces/oc-if:interface/oc-eth:ethernet/oc-eth:state/oc-eth:counters/oc-eth:out-mac-errors-tx" {
		description "Not-supported deviation.";
		deviate "not-supported";
	}
	deviation "/oc-if:interfaces/oc-if:interface/oc-eth:ethernet/oc-vlan:switched-vlan/oc-vlan:state" {
		description "Not-supported deviation.";
		deviate "not-supported";
	}
	deviation "/oc-if:interfaces/oc-if:interface/oc-if:state/oc-if:cpu" {
		description "Not-supported deviation.";
		deviate "not-supported";
	}
	deviation "/oc-if:interfaces/oc-if:interface/oc-if:state/oc-if:logical" {
		description "Not-supported deviation.";
		deviate "not-supported";
	}
	deviation "/oc-if:interfaces/oc-if:interface/oc-if:state/oc-if:counters/oc-if:resets" {
		description "Not-supported deviation.";
		deviate "not-supported";
	}
	deviation "/oc-if:interfaces/oc-if:interface/oc-if:subinterfaces/oc-if:subinterface/oc-if:state/oc-if:cpu" {
		description "Not-supported deviation.";
		deviate "not-supported";
	}
	deviation "/oc-if:interfaces/oc-if:interface/oc-if:subinterfaces/oc-if:subinterface/oc-if:state/oc-if:logical" {
		description "Not-supported deviation.";
		deviate "not-supported";
	}
	deviation "/oc-if:interfaces/oc-if:interface/oc-if:subinterfaces/oc-if:subinterface/oc-if:state/oc-if:management" {
		description "Not-supported deviation.";
		deviate "not-supported";
	}
	deviation "/oc-if:interfaces/oc-if:interface/oc-if:subinterfaces/oc-if:subinterface/oc-if:state/oc-if:counters/oc-if:in-fcs-errors" {
		description "Not-supported deviation.";
		deviate "not-supported";
	}
	deviation "/oc-if:interfaces/oc-if:interface/oc-if:subinterfaces/oc-if:subinterface/oc-if:state/oc-if:counters/oc-if:in-unknown-protos" {
		description "Not-supported deviation.";
		deviate "not-supported";
	}
	deviation "/oc-if:interfaces/oc-if:interface/oc-if:subinterfaces/oc-if:subinterface/oc-if:state/oc-if:counters/oc-if:last-clear" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:accept-mode" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:current-priority" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:preempt" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:preempt-delay" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:priority" {
		description "Not-supported deviation.";
		deviate "not-supported";
	}
	deviation "/oc-if:interfaces/oc-if:interface/oc-if:subinterfaces/oc-if:subinterface/oc-ip:ipv4/oc-ip:addresses/oc-ip:address/oc-ip:vrrp/oc-ip:vrrp-group/oc-ip:state/oc-ip:virtual-router-id" {
		description "Not-supported deviation.";
		deviate "not-supported";
	}
	deviation "/oc-if:interfaces/oc-if:interface/oc-if:subinterfaces/oc-if:subinterface/oc-ip:ipv4/oc-ip:state/oc-ip:counters/oc-ip:in-discarded-pkts" {
		description "Not-supported deviation.";
		deviate "not-supported";
	}
	deviation "/oc-if:interfaces/oc-if:interface/oc-if:subinterfaces/oc-if:subinterface/oc-ip:ipv4/oc-ip:state/oc-ip:counters/oc-ip:in-error-pkts" {
		description "Not-supported deviation.";
		deviate "not-supported";
	}
	deviation "/oc-if:interfaces/oc-if:interface/oc-if:subinterfaces/oc-if:subinterface/oc-ip:ipv4/oc-ip:state/oc-ip:counters/oc-ip:in-forwarded-octets" {
		description "Not-supported deviation.";
		deviate "not-supported";
	}
	deviation "/oc-if:interfaces/oc-if:interface/oc-if:subinterfaces/oc-if:subinterface/oc-ip:ipv4/oc-ip:state/oc-ip:counters/oc-ip:in-forwarded-pkts" {
		description "Not-supported deviation.";
		deviate "not-supported";
	}
	deviation "/oc-if:interfaces/oc-if:interface/oc-if:subinterfaces/oc-if:subinterface/oc-ip:ipv4/oc-ip:state/oc-ip:counters/oc-ip:in-multicast-octets" {
		description "Not-supported deviation.";
		deviate "not-supported";
	}
	deviation "/oc-if:interfaces/oc-if:interface/oc-if:subinterfaces/oc-if:subinterface/oc-ip:ipv4/oc-ip:state/oc-ip:counters/oc-ip:in-multicast-pkts" {
		description "Not-supported deviation.";
		deviate "not-supported";
	}
	deviation "/oc-if:interfaces/oc-if:interface/oc-if:subinterfaces/oc-if:subinterface/oc-ip:ipv4/oc-ip:state/oc-ip:counters/oc-ip:out-discarded-pkts" {
		description "Not-supported deviation.";
		deviate "not-supported";
	}
	deviation "/oc-if:interfaces/oc-if:interface/oc-if:subinterfaces/oc-if:subinterface/oc-ip:ipv4/oc-ip:state/oc-ip:counters/oc-ip:out-error-pkts" {
		description "Not-supported deviation.";
		deviate "not-supported";
	}
	deviation "/oc-if:interfaces/oc-if:interface/oc-if:subinterfaces/oc-if:subinterface/oc-ip:ipv4/oc-ip:state/oc-ip:counters/oc-ip:out-multicast-octets" {
		description "Not-supported deviation.";
		deviate "not-supported";
	}
	deviation "/oc-if:interfaces/oc-if:interface/oc-if:subinterfaces/oc-if:subinterface/oc-ip:ipv4/oc-ip:state/oc-ip:counters/oc-ip:out-multicast-pkts" {
		description "Not-supported deviation.";
		deviate "not-supported";
	}
	deviation "/oc-if:interfaces/oc-if:interface/oc-if:subinterfaces/oc-if:subinterface/oc-ip:ipv6/oc-ip:unnumbered" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:config/oc-ip:virtual-link-local" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:accept-mode" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:current-priority" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:preempt" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:preempt-delay" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:priority" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:virtual-link-local" {
		description "Not-supported deviation.";
		deviate "not-supported";
	}
	deviation "/oc-if:interfaces/oc-if:interface/oc-if:subinterfaces/oc-if:subinterface/oc-ip:ipv6/oc-ip:addresses/oc-ip:address/oc-ip:vrrp/oc-ip:vrrp-group/oc-ip:state/oc-ip:virtual-router-id" {
		description "Not-supported deviation.";
		deviate "not-supported";
	}
	deviation "/oc-if:interfaces/oc-if:interface/oc-if:subinterfaces/oc-if:subinterface/oc-ip:ipv6/oc-ip:config/oc-ip:dup-addr-detect-transmits" {
		description "Not-supported deviation.";
		deviate "not-supported";
	}
	deviation "/oc-if:interfaces/oc-if:interface/oc-if:subinterfaces/oc-if:subinterface/oc-ip:ipv6/oc-ip:router-advertisement/oc-ip:prefixes" {
		description "Not-supported deviation.";
		deviate "not-supported";
	}
	deviation "/oc-if:interfaces/oc-if:interface/oc-if:subinterfaces/oc-if:subinterface/oc-ip:ipv6/oc-ip:router-advertisement/oc-ip:config/oc-ip:interval" {
		description "Not-supported deviation.";
		deviate "not-supported";
	}
	deviation "/oc-if:interfaces/oc-if:interface/oc-if:subinterfaces/oc-if:subinterface/oc-ip:ipv6/oc-ip:router-advertisement/oc-ip:config/oc-ip:lifetime" {
		description "Not-supported deviation.";
		deviate "not-supported";
	}
	deviation "/oc-if:interfaces/oc-if:interface/oc-if:subinterfaces/oc-if:subinterface/oc-ip:ipv6/oc-ip:router-advertisement/oc-ip:config/oc-ip:managed" {
		description "Not-supported deviation.";
		deviate "not-supported";
	}
	deviation "/oc-if:interfaces/oc-if:interface/oc-if:subinterfaces/oc-if:subinterface/oc-ip:ipv6/oc-ip:router-advertisement/oc-ip:config/oc-ip:other-config" {
		description "Not-supported deviation.";
		deviate "not-supported";
	}
	deviation "/oc-if:interfaces/oc-if:interface/oc-if:subinterfaces/oc-if:subinterface/oc-ip:ipv6/oc-ip:router-advertisement/oc-ip:config/oc-ip:suppress" {
		description "Not-supported deviation.";
		deviate "not-supported";
	}
	deviation "/oc-if:interfaces/oc-if:interface/oc-if:subinterfaces/oc-if:subinterface/oc-ip:ipv6/oc-ip:router-advertisement/oc-ip:state/oc-ip:interval" {
		description "Not-supported deviation.";
		deviate "not-supported";
	}
	deviation "/oc-if:interfaces/oc-if:interface/oc-if:subinterfaces/oc-if:subinterface/oc-ip:ipv6/oc-ip:router-advertisement/oc-ip:state/oc-ip:lifetime" {
		description "Not-supported deviation.";
		deviate "not-supported";
	}
	deviation "/oc-if:interfaces/oc-if:interface/oc-if:subinterfaces/oc-if:subinterface/oc-ip:ipv6/oc-ip:router-advertisement/oc-ip:state/oc-ip:managed" {
		description "Not-supported deviation.";
		deviate "not-supported";
	}
	deviation "/oc-if:interfaces/oc-if:interface/oc-if:subinterfaces/oc-if:subinterface/oc-ip:ipv6/oc-ip:router-advertisement/oc-ip:state/oc-ip:other-config" {
		description "Not-supported deviation.";
		deviate "not-supported";
	}
	deviation "/oc-if:interfaces/oc-if:interface/oc-if:subinterfaces/oc-if:subinterface/oc-ip:ipv6/oc-ip:router-advertisement/oc-ip:state/oc-ip:suppress" {
		description "Not-supported deviation.";
		deviate "not-supported";
	}
	deviation "/oc-if:interfaces/oc-if:interface/oc-if:subinterfaces/oc-if:subinterface/oc-ip:ipv6/oc-ip:state/oc-ip:dup-addr-detect-transmits" {
		description "Not-supported deviation.";
		deviate "not-supported";
	}
	deviation "/oc-if:interfaces/oc-if:interface/oc-if:subinterfaces/oc-if:subinterface/oc-ip:ipv6/oc-ip:state/oc-ip:counters/oc-ip:in-discarded-pkts" {
		description "Not-supported deviation.";
		deviate "not-supported";
	}
	deviation "/oc-if:interfaces/oc-if:interface/oc-if:subinterfaces/oc-if:subinterface/oc-ip:ipv6/oc-ip:state/oc-ip:counters/oc-ip:in-error-pkts" {
		description "Not-supported deviation.";
		deviate "not-supported";
	}
	deviation "/oc-if:interfaces/oc-if:interface/oc-if:subinterfaces/oc-if:subinterface/oc-ip:ipv6/oc-ip:state/oc-ip:counters/oc-ip:in-forwarded-octets" {
		description "Not-supported deviation.";
		deviate "not-supported";
	}
	deviation "/oc-if:interfaces/oc-if:interface/oc-if:subinterfaces/oc-if:subinterface/oc-ip:ipv6/oc-ip:state/oc-ip:counters/oc-ip:in-forwarded-pkts" {
		description "Not-supported deviation.";
		deviate "not-supported";
	}
	deviation "/oc-if:interfaces/oc-if:interface/oc-if:subinterfaces/oc-if:subinterface/oc-ip:ipv6/oc-ip:state/oc-ip:counters/oc-ip:in-multicast-octets" {
		description "Not-supported deviation.";
		deviate "not-supported";
	}
	deviation "/oc-if:interfaces/oc-if:interface/oc-if:subinterfaces/oc-if:subinterface/oc-ip:ipv6/oc-ip:state/oc-ip:counters/oc-ip:in-multicast-pkts" {
		description "Not-supported deviation.";
		deviate "not-supported";
	}
	deviation "/oc-if:interfaces/oc-if:interface/oc-if:subinterfaces/oc-if:subinterface/oc-ip:ipv6/oc-ip:state/oc-ip:counters/oc-ip:out-discarded-pkts" {
		description "Not-supported deviation.";
		deviate "not-supported";
	}
	deviation "/oc-if:interfaces/oc-if:interface/oc-if:subinterfaces/oc-if:subinterface/oc-ip:ipv6/oc-ip:state/oc-ip:counters/oc-ip:out-error-pkts" {
		description "Not-supported deviation.";
		deviate "not-supported";
	}
	deviation "/oc-if:interfaces/oc-if:interface/oc-if:subinterfaces/oc-if:subinterface/oc-ip:ipv6/oc-ip:state/oc-ip:counters/oc-ip:out-multicast-octets" {
		description "Not-supported deviation.";
		deviate "not-supported";
	}
	deviation "/oc-if:interfaces/oc-if:interface/oc-if:subinterfaces/oc-if:subinterface/oc-ip:ipv6/oc-ip:state/oc-ip:counters/oc-ip:out-multicast-pkts" {
		description "Not-supported deviation.";
		deviate "not-supported";
	}
	deviation "/oc-if:interfaces/oc-if:interface/oc-if:subinterfaces/oc-if:subinterface/oc-vlan:vlan/oc-vlan:egress-mapping" {
		description "Not-supported deviation.";
		deviate "not-supported";
	}
	deviation "/oc-if:interfaces/oc-if:interface/oc-if:subinterfaces/oc-if:subinterface/oc-vlan:vlan/oc-vlan:ingress-mapping" {
		description "Not-supported deviation.";
		deviate "not-supported";
	}
	deviation "/oc-if:interfaces/oc-if:interface/oc-if:subinterfaces/oc-if:subinterface/oc-vlan:vlan/oc-vlan:match/oc-vlan:double-tagged" {
		description "Not-supported deviation.";
		deviate "not-supported";
	}
	deviation "/oc-if:interfaces/oc-if:interface/oc-if:subinterfaces/oc-if:subinterface/oc-vlan:vlan/oc-vlan:match/oc-vlan:double-tagged-inner-list" {
		description "Not-supported deviation.";
		deviate "not-supported";
	}
	deviation "/oc-if:interfaces/oc-if:interface/oc-if:subinterfaces/oc-if:subinterface/oc-vlan:vlan/oc-vlan:match/oc-vlan:double-tagged-inner-outer-range" {
		description "Not-supported deviation.";
		deviate "not-supported";
	}
	deviation "/oc-if:interfaces/oc-if:interface/oc-if:subinterfaces/oc-if:subinterface/oc-vlan:vlan/oc-vlan:match/oc-vlan:double-tagged-inner-range" {
		description "Not-supported deviation.";
		deviate "not-supported";
	}
	deviation "/oc-if:interfaces/oc-if:interface/oc-if:subinterfaces/oc-if:subinterface/oc-vlan:vlan/oc-vlan:match/oc-vlan:double-tagged-outer-list" {
		description "Not-supported deviation.";
		deviate "not-supported";
	}
	deviation "/oc-if:interfaces/oc-if:interface/oc-if:subinterfaces/oc-if:subinterface/oc-vlan:vlan/oc-vlan:match/oc-vlan:double-tagged-outer-range" {
		description "Not-supported deviation.";
		deviate "not-supported";
	}
	deviation "/oc-if:interfaces/oc-if:interface/oc-if:subinterfaces/oc-if:subinterface/oc-vlan:vlan/oc-vlan:match/oc-vlan:single-tagged-list" {
		description "Not-supported deviation.";
		deviate "not-supported";
	}
	deviation "/oc-if:interfaces/oc-if:interface/oc-if:subinterfaces/oc-if:subinterface/oc-vlan:vlan/oc-vlan:match/oc-vlan:single-tagged-range" {
		description "Not-supported deviation.";
		deviate "not-supported";
	}
	deviation "/oc-if:interfaces/oc-if:interface/oc-lag:aggregation/oc-vlan:switched-vlan/oc-vlan:state" {
		description "Not-supported deviation.";
		deviate "not-supported";
	}
	deviation "/oc-if:interfaces/oc-if:interface/oc-tun:tunnel/oc-tun:ipv4" {
		description "Not-supported deviation.";
		deviate "not-supported";
	}
	deviation "/oc-if:interfaces/oc-if:interface/oc-tun:tunnel/oc-tun:ipv6" {
		description "Not-supported deviation.";
		deviate "not-supported";
	}
	deviation "/oc-if:interfaces/oc-if:interface/oc-vlan:routed-vlan/oc-ip:ipv4/oc-ip:neighbors" {
		description "Not-supported deviation.";
		deviate "not-supported";
	}
	deviation "/oc-if:interfaces/oc-if:interface/oc-vlan:routed-vlan/oc-ip:ipv4/oc-ip:proxy-arp" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:accept-mode" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:current-priority" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:preempt" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:preempt-delay" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:priority" {
		description "Not-supported deviation.";
		deviate "not-supported";
	}
	deviation "/oc-if:interfaces/oc-if:interface/oc-vlan:routed-vlan/oc-ip:ipv4/oc-ip:addresses/oc-ip:address/oc-ip:vrrp/oc-ip:vrrp-group/oc-ip:state/oc-ip:virtual-router-id" {
		description "Not-supported deviation.";
		deviate "not-supported";
	}
	deviation "/oc-if:interfaces/oc-if:interface/oc-vlan:routed-vlan/oc-ip:ipv4/oc-ip:config/oc-ip:dhcp-client" {
		description "Not-supported deviation.";
		deviate "not-supported";
	}
	deviation "/oc-if:interfaces/oc-if:interface/oc-vlan:routed-vlan/oc-ip:ipv4/oc-ip:state/oc-ip:counters" {
		description "Not-supported deviation.";
		deviate "not-supported";
	}
	deviation "/oc-if:interfaces/oc-if:interface/oc-vlan:routed-vlan/oc-ip:ipv4/oc-ip:state/oc-ip:dhcp-client" {
		description "Not-supported deviation.";
		deviate "not-supported";
	}
	deviation "/oc-if:interfaces/oc-if:interface/oc-vlan:routed-vlan/oc-ip:ipv4/oc-ip:state/oc-ip:enabled" {
		description "Not-supported deviation.";
		deviate "not-supported";
	}
	deviation "/oc-if:interfaces/oc-if:interface/oc-vlan:routed-vlan/oc-ip:ipv6/oc-ip:neighbors" {
		description "Not-supported deviation.";
		deviate "not-supported";
	}
	deviation "/oc-if:interfaces/oc-if:interface/oc-vlan:routed-vlan/oc-ip:ipv6/oc-ip:unnumbered" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:config/oc-ip:virtual-link-local" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:accept-mode" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:current-priority" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:preempt" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:preempt-delay" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:priority" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:virtual-link-local" {
		description "Not-supported deviation.";
		deviate "not-supported";
	}
	deviation "/oc-if:interfaces/oc-if:interface/oc-vlan:routed-vlan/oc-ip:ipv6/oc-ip:addresses/oc-ip:address/oc-ip:vrrp/oc-ip:vrrp-group/oc-ip:state/oc-ip:virtual-router-id" {
		description "Not-supported deviation.";
		deviate "not-supported";
	}
	deviation "/oc-if:interfaces/oc-if:interface/oc-vlan:routed-vlan/oc-ip:ipv6/oc-ip:config/oc-ip:dhcp-client" {
		description "Not-supported deviation.";
		deviate "not-supported";
	}
	deviation "/oc-if:interfaces/oc-if:interface/oc-vlan:routed-vlan/oc-ip:ipv6/oc-ip:config/oc-ip:dup-addr-detect-transmits" {
		description "Not-supported deviation.";
		deviate "not-supported";
	}
	deviation "/oc-if:interfaces/oc-if:interface/oc-vlan:routed-vlan/oc-ip:ipv6/oc-ip:router-advertisement/oc-ip:prefixes" {
		description "Not-supported deviation.";
		deviate "not-supported";
	}
	deviation "/oc-if:interfaces/oc-if:interface/oc-vlan:routed-vlan/oc-ip:ipv6/oc-ip:router-advertisement/oc-ip:config/oc-ip:interval" {
		description "Not-supported deviation.";
		deviate "not-supported";
	}
	deviation "/oc-if:interfaces/oc-if:interface/oc-vlan:routed-vlan/oc-ip:ipv6/oc-ip:router-advertisement/oc-ip:config/oc-ip:lifetime" {
		description "Not-supported deviation.";
		deviate "not-supported";
	}
	deviation "/oc-if:interfaces/oc-if:interface/oc-vlan:routed-vlan/oc-ip:ipv6/oc-ip:router-advertisement/oc-ip:config/oc-ip:managed" {
		description "Not-supported deviation.";
		deviate "not-supported";
	}
	deviation "/oc-if:interfaces/oc-if:interface/oc-vlan:routed-vlan/oc-ip:ipv6/oc-ip:router-advertisement/oc-ip:config/oc-ip:other-config" {
		description "Not-supported deviation.";
		deviate "not-supported";
	}
	deviation "/oc-if:interfaces/oc-if:interface/oc-vlan:routed-vlan/oc-ip:ipv6/oc-ip:router-advertisement/oc-ip:config/oc-ip:suppress" {
		description "Not-supported deviation.";
		deviate "not-supported";
	}
	deviation "/oc-if:interfaces/oc-if:interface/oc-vlan:routed-vlan/oc-ip:ipv6/oc-ip:router-advertisement/oc-ip:state/oc-ip:interval" {
		description "Not-supported deviation.";
		deviate "not-supported";
	}
	deviation "/oc-if:interfaces/oc-if:interface/oc-vlan:routed-vlan/oc-ip:ipv6/oc-ip:router-advertisement/oc-ip:state/oc-ip:lifetime" {
		description "Not-supported deviation.";
		deviate "not-supported";
	}
	deviation "/oc-if:interfaces/oc-if:interface/oc-vlan:routed-vlan/oc-ip:ipv6/oc-ip:router-advertisement/oc-ip:state/oc-ip:managed" {
		description "Not-supported deviation.";
		deviate "not-supported";
	}
	deviation "/oc-if:interfaces/oc-if:interface/oc-vlan:routed-vlan/oc-ip:ipv6/oc-ip:router-advertisement/oc-ip:state/oc-ip:other-config" {
		description "Not-supported deviation.";
		deviate "not-supported";
	}
	deviation "/oc-if:interfaces/oc-if:interface/oc-vlan:routed-vlan/oc-ip:ipv6/oc-ip:router-advertisement/oc-ip:state/oc-ip:suppress" {
		description "Not-supported deviation.";
		deviate "not-supported";
	}
	deviation "/oc-if:interfaces/oc-if:interface/oc-vlan:routed-vlan/oc-ip:ipv6/oc-ip:state/oc-ip:counters" {
		description "Not-supported deviation.";
		deviate "not-supported";
	}
	deviation "/oc-if:interfaces/oc-if:interface/oc-vlan:routed-vlan/oc-ip:ipv6/oc-ip:state/oc-ip:dhcp-client" {
		description "Not-supported deviation.";
		deviate "not-supported";
	}
	deviation "/oc-if:interfaces/oc-if:interface/oc-vlan:routed-vlan/oc-ip:ipv6/oc-ip:state/oc-ip:dup-addr-detect-transmits" {
		description "Not-supported deviation.";
		deviate "not-supported";
	}
	deviation "/oc-if:interfaces/oc-if:interface/oc-vlan:routed-vlan/oc-ip:ipv6/oc-ip:state/oc-ip:enabled" {
		description "Not-supported deviation.";
		deviate "not-supported";
	}
}
