module "arista-ale-counters-open-config-hardware-drop-counters" {
	yang-version "1";
	namespace "http://arista.com/yang/experimental/eos/arista-ale-counters-open-config-hardware-drop-counters";
	prefix "arista-ale-counters-open-config-hardware-drop-counters";
	import "openconfig-extensions" {
		prefix "oc-ext";
	}
	organization "Arista Networks <http://arista.com/>";
	contact "Arista Networks <http://arista.com/>";
	description "Hardware drop reason counters
	             
	             THIS YANG MODULE WAS GENERATED. DO NOT EDIT THIS FILE.";
	oc-ext:openconfig-version "1.0.0";
	revision "2023-01-01" {
		description "Version 1.0.0, generated on 2023-01-01";
		reference "1.0.0";
	}
	grouping "hardware-drop-adverse-block-state" {
		leaf "ipt-crc-error" {
			type "uint64";
			description "Packet corruption in DRAM. These packets are dropped because the CRC covering the packet and internal headers was wrong after reading the packet from DRAM memory.";
		}
		leaf "unicast-fifo" {
			type "uint64";
			description "Ingress unicast oversubscription. Occurs when the buffer used for storing unicast traffic reaches its maximum capacity.";
		}
		leaf "unicast-fifo-sflow" {
			type "uint64";
			description "Ingress unicast oversubscription. Occurs when the buffer used for replicating unicast traffic for sFlow monitoring reaches its maximum capacity.";
		}
		leaf "unicast-fifo-snoop" {
			type "uint64";
			description "Ingress unicast oversubscription. Occurs when the buffer used for replicating unicast traffic for snooping reaches its maximum capacity.";
		}
		leaf "ingress-repl-fifo" {
			type "uint64";
			description "Ingress replication oversubscription. Occurs when the buffer used for replicating ingress traffic reaches its maximum capacity.";
		}
		leaf "ingress-repl-fifo-sflow" {
			type "uint64";
			description "Ingress replication oversubscription.Occurs when the buffer used for replicating ingress traffic for sFlow reaches its maximum capacity.";
		}
		leaf "ingress-repl-fifo-snoop" {
			type "uint64";
			description "Ingress replication oversubscription.Occurs when the buffer used for replicating ingress traffic for snooping reaches its maximum capacity.";
		}
		leaf "ingress-repl-fifo-mirror" {
			type "uint64";
			description "Ingress replication oversubscription.Occurs when the buffer used for replicating ingress traffic for mirroring reaches its maximum capacity.";
		}
		leaf "dequeue-delete" {
			type "uint64";
			description "Stale packets in VOQs, e.g., starvation in low priority queues when strict priority queuing is used, flow control being asserted on a port, or egress queuing block getting stuck.";
		}
		leaf "dram-full" {
			type "uint64";
			description "Packets dropped due to DRAM buffer exhaustion.";
		}
		leaf "rqp-discard" {
			type "uint64";
			description "Fabric reassembly discarded packets. These packets are dropped due to cell reassembly errors on egress, could be due to missing cell or mismatch in packet CRC. This indicates an issue with the FAP or fabric serdes.";
		}
		leaf "egress-unicast-no-data-buffer-for-port-or-queue" {
			type "uint64";
			description "Unicast packets dropped on egress due to lack of available unicast data-buffers for a port or queue.";
		}
		leaf "egress-unicast-no-data-buffer" {
			type "uint64";
			description "Unicast packets dropped at reassembly stage on egress due to lack of available unicast data-buffers at a core or device level.";
		}
		leaf "multicast-no-data-buffer" {
			type "uint64";
			description "Multicast packets dropped due to lack of buffers. These multicast packets are dropped because of lack of global egress buffers.";
		}
		leaf "fabric-receive-cell" {
			type "uint64";
			description "Fabric receive cell discards. These cells were dropped due to oversubscription.";
		}
		leaf "mesh-multicast-repl" {
			type "uint64";
			description "Number of multicast mesh replication packets that have been discarded.";
		}
		leaf "egress-multicast-repl-low" {
			type "uint64";
			description "Number of low priority egress multicast replication packets that are dropped.";
		}
		leaf "egress-multicast-repl-high" {
			type "uint64";
			description "Number of high priority egress multicast replication packets that are dropped.";
		}
		leaf "egress-unicast-repl" {
			type "uint64";
			description "Number of unicast egress replication packets that have been discarded.";
		}
		leaf "ingress-reassembly" {
			type "uint64";
			description "Number of packets discarded due to reassembly errors.";
		}
		leaf "egress-aligner" {
			type "uint64";
			description "Number of packets that have been dropped at the egress packet network interface due to errors such as packet CRC failures, alignment issues, or other errors.";
		}
		leaf "serdes-crc-error" {
			type "uint64";
			description "Weak serdes link between the fabric chip and forwarding engine. Sometimes due to a marginal connection that could be fixed by module re-insertion. Strongly correlated with both dch-reordered and rqp discards.";
		}
		leaf "dch-fifo" {
			type "uint64";
			description "Fabric cell drop at ingress.";
		}
		leaf "dch-reordered" {
			type "uint64";
			description "Linecard restarts, insertions, or removals can result in temporary disruptions in the fabric links of the device, potentially causing the system to re-tune the links. This may lead to an increase in this counter due to CRC errors.";
		}
		leaf "dch-unreachable" {
			type "uint64";
			description "DCH unreachable indicates the cells that were sent to fabric but did not have a valid 'destination ID' and were therefore dropped.";
		}
		leaf "dch-fifo-multicast-low" {
			type "uint64";
			description "Fabric cell drops of low priority multicast at ingress.";
		}
		leaf "rtp-drh-multicast-low" {
			type "uint64";
			description "Fabric cell drops of low priority multicast due to replication oversubscription.";
		}
		leaf "dcm-fifo-ip" {
			type "uint64";
			description "Unicast packet cell (internal packet fragment) dropped due to FIFOs overflow. Due to misconfiguration or hardware issue.";
		}
		leaf "dcm-fifo-total" {
			type "uint64";
			description "Unicast and fabric multicast cells dropped due to FIFO overflow. For multicast this could be due to system multicast oversubscription for unicast should not happen.";
		}
		leaf "dcl-fifo-total" {
			type "uint64";
			description "Total packets dropped at DCL block regardless of priority.";
		}
		leaf "ingress-forwarding-lookup-miss" {
			type "uint64";
			description "A routed packet did not hit any route in the LPM. This is indicative of a bug because we should always install a default route.";
		}
		leaf "ingress-no-forwarding-action" {
			type "uint64";
			description "The packet failed to be forwarded by any means. This usually indicates a bug.";
		}
		description "The adverse drops are the abnormal drop conditions that can lead to significant packet loss.";
	}
	grouping "hardware-drop-adverse-block" {
		container "state" {
			uses "hardware-drop-adverse-block-state";
			description "Adverse attributes";
		}
		description "Adverse block";
	}
	grouping "hardware-drop-packet-processor-block-state" {
		leaf "ingress-port-not-vlan-member" {
			type "uint64";
			description "Counts packets dropped due to VLAN membership filtering, missing data on L2 subinterfaces, incorrect switchport VLAN mapping, and temporarily misconfigured routed ports.";
		}
		leaf "ingress-sa-equals-da" {
			type "uint64";
			description "Counts packets dropped due to MAC source and destination address are the same.";
		}
		leaf "ingress-sa-multicast" {
			type "uint64";
			description "Counts packets dropped due to illegal L2 frames having a multicast source address.";
		}
		leaf "ingress-rpf" {
			type "uint64";
			description "Counts packets dropped due to RPF check failures.";
		}
		leaf "ingress-ip-version-error" {
			type "uint64";
			description "Counts packets dropped due to illegal IP version.";
		}
		leaf "ingress-ipv4-checksum-error" {
			type "uint64";
			description "Counts packets dropped due to illegal IPv4 checksum errors.";
		}
		leaf "ingress-ip-ttl0" {
			type "uint64";
			description "Counts packets dropped due to IP TTL value is 0.";
		}
		leaf "ingress-ipv6-unspecified-destination" {
			type "uint64";
			description "Counts packets dropped due to IPv6 dst-IP being 0.";
		}
		leaf "ingress-ipv6-multicast-source" {
			type "uint64";
			description "Counts packets dropped because IPv6 source address is multicast.";
		}
		leaf "ingress-acl" {
			type "uint64";
			description "Counts packets dropped due to ACL filtering.";
		}
		leaf "ingress-no-arp" {
			type "uint64";
			description "Counts packets dropped because ARP or IPv6 Neighbor Discovery has not been resolved for the directly attached host.";
		}
		leaf "ingress-null-route" {
			type "uint64";
			description "Counts packets dropped due to hitting a route set to drop them, typically occurring when the destination of a tunnel (e.g., VXLAN/nexthop groups) cannot be determined or when the default route is configured for dropping.";
		}
		leaf "ingress-arp-capacity" {
			type "uint64";
			description "Counts packets destined to an unresolved host that were dropped because the ARP cache is full.";
		}
		leaf "ingress-pbr" {
			type "uint64";
			description "Counts packets dropped by PBR.";
		}
		leaf "egress-mtu-tunnel" {
			type "uint64";
			description "Counts packets dropped due to MTU violation.";
		}
		leaf "ingress-ptp" {
			type "uint64";
			description "Counts multicast PTP packets when PTP forward unicast is enabled. A copy of the packet is sent to CPU.";
		}
		leaf "ingress-lag" {
			type "uint64";
			description "Counts of packets dropped at the ingress of LAG members that failed to negotiate LACP.";
		}
		leaf "ingress-multicast-no-cpu" {
			type "uint64";
			description "A broadcast packet in a VLAN that is not attached to an SVI will have a copy dropped due to this reason. It is completely expected.";
		}
		leaf "ingress-sa-not-found" {
			type "uint64";
			description "This is either bidirectional PIM packets that fail the DF check or packets that fail the source address check when 802.1X MAB is enabled.";
		}
		leaf "egress-acl" {
			type "uint64";
			description "Counts packets that hit egress ACLs and get dropped.";
		}
		leaf "ingress-multicast-empty-mcid" {
			type "uint64";
			description "This means that an internal copy of replicated packet is being dropped which would go to the CPU if this was L3 multicast chain. But it should be dropped in case L2 uses L3 multicast chain. These are legitimate drops.";
		}
		leaf "egress-multicast-routed-ttl" {
			type "uint64";
			description "Counts multicast routed packets dropped with TTL 1.";
		}
		leaf "ingress-intf-mpls-disabled" {
			type "uint64";
			description "Received an MPLS packet on an interface where MPLS routing is disabled.";
		}
		leaf "ingress-source-port-filter" {
			type "uint64";
			description "A unicast bridged packet was sent to the same port it ingressed on.";
		}
		leaf "ingress-encap-bum-filter" {
			type "uint64";
			description "Counts packets dropped due to encap BUM filter.";
		}
		leaf "ingress-etree-leaf" {
			type "uint64";
			description "Unknown unicast drops for E-Tree leaf.";
		}
		leaf "ingress-oam" {
			type "uint64";
			description "Drop packets received at wrong MD (Maintainance Domains) levels at ingress side.";
		}
		leaf "ingress-vpls-standby-pseudowire" {
			type "uint64";
			description "Drop packets received on standby pseudowire.";
		}
		leaf "ingress-meter" {
			type "uint64";
			description "Counts packets dropped that exceed the configured meter rate limit.";
		}
		description "These counters represent the conditions in which packets are dropped due to legitimate forwarding decisions (configured to do so) - ACL drops, No Route, STP filtering, etc.";
	}
	grouping "hardware-drop-packet-processor-block" {
		container "state" {
			uses "hardware-drop-packet-processor-block-state";
			description "Packet processor attributes";
		}
		description "Packet processor block";
	}
	grouping "hardware-drop-congestion-block-state" {
		leaf "unicast-fifo-mirror" {
			type "uint64";
			description "Ingress unicast oversubscription. Occurs when the buffer used for replicating unicast traffic for mirroring reaches its maximum capacity.";
		}
		description "Congestion drop attributes";
	}
	grouping "hardware-drop-congestion-block" {
		container "state" {
			uses "hardware-drop-congestion-block-state";
			description "Congestion drop attributes";
		}
		description "Congestion block";
	}
	grouping "pipeline-arista-sand-hardware-drop-counters" {
		container "adverse" {
			uses "hardware-drop-adverse-block";
			description "Adverse block";
		}
		container "packet-processor" {
			uses "hardware-drop-packet-processor-block";
			description "Packet processor block";
		}
		container "congestion" {
			uses "hardware-drop-congestion-block";
			description "Congestion block";
		}
		description "Container for Sand specific hardware drop counters.";
	}
	grouping "pipeline-arista-hardware-drop-counters" {
		container "sand" {
			uses "pipeline-arista-sand-hardware-drop-counters";
			description "Container for Sand specific drop counters.";
		}
		description "";
	}
	grouping "pipeline-vendor-hardware-drop-counters" {
		container "arista" {
			uses "pipeline-arista-hardware-drop-counters";
			description "Container for Arista-specific drop counters.";
		}
		description "";
	}
}
