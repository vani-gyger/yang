module "arista-pseudowire-pseudowire-status" {
	yang-version "1";
	namespace "http://arista.com/yang/experimental/eos/arista-pseudowire-pseudowire-status";
	prefix "arista-pseudowire-pseudowire-status";
	import "openconfig-extensions" {
		prefix "oc-ext";
	}
	import "arista-ebra-intf-encap" {
		prefix "arista-ebra-intf-encap";
	}
	import "arista-ebra-vlan-tpid" {
		prefix "arista-ebra-vlan-tpid";
	}
	import "arista-exp-eos" {
		prefix "arista-exp-eos";
	}
	import "arista-tunnel-tunnel-basic-types" {
		prefix "arista-tunnel-tunnel-basic-types";
	}
	import "openconfig-interfaces" {
		prefix "openconfig-interfaces";
	}
	import "openconfig-mpls-types" {
		prefix "openconfig-mpls-types";
	}
	organization "Arista Networks <http://arista.com/>";
	contact "Arista Networks <http://arista.com/>";
	description "Pseudowire status model for LDP PW and VPWS. Contains all
	              active Pseudowire patches. Each patch has an administratively given name, and can
	              either connect two local interfaces (local-local patch) or a set of local interfaces
	              to a remote destination (local-remote patch). The remote destination can be single
	              or multi-homed, and can be reachable via one or multiple tunnels.
	             
	              For local-remote patches, a pseudowire interface identifies the remote connector of
	              the patch. The local end is always identified by a local interface.
	             
	             THIS YANG MODULE WAS GENERATED. DO NOT EDIT THIS FILE.";
	oc-ext:openconfig-version "1.0.0";
	revision "2021-10-20" {
		description "Version 1.0.0, generated on 2021-10-20";
		reference "1.0.0";
	}
	typedef "pw-encap-tunnel-group-id" {
		type "uint32";
		description "Opaque handle identifying a group of MPLS tunnels used for encapsulating Pseudowire traffic.";
	}
	grouping "pw-encap-tunnel" {
		leaf "tunnel-id" {
			type "arista-tunnel-tunnel-basic-types:tunnel-id";
			description "Tunnel for encapsulating traffic to the remote destination";
		}
		leaf "peer-label" {
			type "openconfig-mpls-types:mpls-label";
			description "MPLS (pseudowire) label used for encapsulating traffic to the remote destination";
		}
		leaf "flow-label" {
			type "boolean";
			description "Traffic to the remote includes a flow label in the MPLS label stack";
		}
		leaf "control-word" {
			type "boolean";
			description "Traffic to the remote includes a control word between the MPLS label stack and the payload";
		}
		description "Encapsulation information for an individual tunnel.";
	}
	grouping "pw-encap-tunnel-group" {
		leaf "pw-encap-tunnel-group-id" {
			type "pw-encap-tunnel-group-id";
			description "Opaque identifier for the group";
		}
		list "pw-encap-tunnel-group" {
			key "tunnel-id peer-label flow-label control-word";
			leaf "tunnel-id" {
				type "arista-tunnel-tunnel-basic-types:tunnel-id";
				description "Tunnel for encapsulating traffic to the remote destination";
			}
			leaf "peer-label" {
				type "openconfig-mpls-types:mpls-label";
				description "MPLS (pseudowire) label used for encapsulating traffic to the remote destination";
			}
			leaf "flow-label" {
				type "boolean";
				description "Traffic to the remote includes a flow label in the MPLS label stack";
			}
			leaf "control-word" {
				type "boolean";
				description "Traffic to the remote includes a control word between the MPLS label stack and the payload";
			}
			description "List of tunnels in the group";
		}
		description "A group of pseudowire encap tunnels used for carrying
		             intf-vlan-encap packets.";
	}
	grouping "intf-vlan-map-entry" {
		container "source-intf-encap" {
			uses "arista-ebra-intf-encap:intf-vlan-encap";
			description "Match packets with this intf-vlan-encap";
		}
		container "dest-intf-encap" {
			uses "arista-ebra-intf-encap:intf-vlan-encap";
			description "Manipulate and forward according to this intf-vlan-encap";
		}
		leaf "retain-outer-cos" {
			type "boolean";
			description "Whether CoS bits in the outer VLAN header must be retained when forwarding";
		}
		leaf "retain-inner-cos" {
			type "boolean";
			description "Whether CoS bits in the inner VLAN header must be retained when forwarding";
		}
		description "Pseudowire traffic source and destination along with tag manipulation";
	}
	grouping "patch-to-local-intf-vlan-group" {
		leaf "patch-name" {
			type "string";
			description "The administratively given name of the patch";
		}
		leaf "is-local-local" {
			type "boolean";
			description "Distinguish local-local and local-remote patch";
		}
		list "local-intf-vlan-group" {
			key "intf-id encap__outer__vid encap__outer__tpid encap__outer__priority encap__inner__vid encap__inner__tpid encap__inner__priority";
			leaf "intf-id" {
				type "openconfig-interfaces:interface-id";
				description "The interface";
			}
			leaf "encap__outer__vid" {
				type "uint16";
				description "VLAN identifier (VID). Values greater than 4094 have special meaning.";
			}
			leaf "encap__outer__tpid" {
				type "arista-ebra-vlan-tpid:vlan-tpid";
				description "Tag protocol identifier (TPID)";
			}
			leaf "encap__outer__priority" {
				type "uint8";
				description "Priority code point (PCP)";
			}
			leaf "encap__inner__vid" {
				type "uint16";
				description "VLAN identifier (VID). Values greater than 4094 have special meaning.";
			}
			leaf "encap__inner__tpid" {
				type "arista-ebra-vlan-tpid:vlan-tpid";
				description "Tag protocol identifier (TPID)";
			}
			leaf "encap__inner__priority" {
				type "uint8";
				description "Priority code point (PCP)";
			}
			description "The list of local intf-vlan-encap entries used by this patch";
		}
		leaf "name" {
			type "string";
			description "name of the grouping";
		}
		description "Map patch name to the local intf-vlan-encap entries";
	}
	grouping "remote-connector-to-local-intf" {
		leaf "pw-intf-id" {
			type "openconfig-interfaces:interface-id";
			description "Opaque key identifying the remote connector of the pseudowire patch. References the intf portion of intf-vlan-encap enties.";
		}
		leaf "patch-name" {
			type "string";
			description "The administratively given name of the patch";
		}
		list "local-intf-ids" {
			key "local-intf-ids-key";
			leaf "local-intf-ids-key" {
				type "openconfig-interfaces:interface-id";
				description "openconfig-interfaces:interface-id key for local-intf-ids list.";
			}
			description "The list of local interfaces that are part of this patch";
		}
		description "Map remote connector to local interfaces";
	}
	grouping "status" {
		list "pw-encap-intf-vlan-map" {
			key "source-intf-encap__intf-id source-intf-encap__encap__outer__vid source-intf-encap__encap__outer__tpid source-intf-encap__encap__outer__priority source-intf-encap__encap__inner__vid source-intf-encap__encap__inner__tpid source-intf-encap__encap__inner__priority";
			leaf "source-intf-encap__intf-id" {
				type "leafref" {
					path "../source-intf-encap/intf-id";
				}
				description "The interface";
			}
			leaf "source-intf-encap__encap__outer__vid" {
				type "leafref" {
					path "../source-intf-encap/encap/outer/vid";
				}
				description "VLAN identifier (VID). Values greater than 4094 have special meaning.";
			}
			leaf "source-intf-encap__encap__outer__tpid" {
				type "leafref" {
					path "../source-intf-encap/encap/outer/tpid";
				}
				description "Tag protocol identifier (TPID)";
			}
			leaf "source-intf-encap__encap__outer__priority" {
				type "leafref" {
					path "../source-intf-encap/encap/outer/priority";
				}
				description "Priority code point (PCP)";
			}
			leaf "source-intf-encap__encap__inner__vid" {
				type "leafref" {
					path "../source-intf-encap/encap/inner/vid";
				}
				description "VLAN identifier (VID). Values greater than 4094 have special meaning.";
			}
			leaf "source-intf-encap__encap__inner__tpid" {
				type "leafref" {
					path "../source-intf-encap/encap/inner/tpid";
				}
				description "Tag protocol identifier (TPID)";
			}
			leaf "source-intf-encap__encap__inner__priority" {
				type "leafref" {
					path "../source-intf-encap/encap/inner/priority";
				}
				description "Priority code point (PCP)";
			}
			uses "intf-vlan-map-entry";
			description "Forwarding of traffic from local connectors. The traffic is classified by local interface and VLAN tags. The destination refers to either a local interface (for local-local patches) or a pseudowire interface (for local-remote patches), and includes the desired VLAN tag manipulation action.";
		}
		list "patch-to-local-intf-vlan-groups" {
			key "patch-name";
			uses "patch-to-local-intf-vlan-group";
			description "Map patch name to the local intf-vlan entries";
		}
		list "pw-decap-intf-vlan-map" {
			key "source-intf-encap__intf-id source-intf-encap__encap__outer__vid source-intf-encap__encap__outer__tpid source-intf-encap__encap__outer__priority source-intf-encap__encap__inner__vid source-intf-encap__encap__inner__tpid source-intf-encap__encap__inner__priority";
			leaf "source-intf-encap__intf-id" {
				type "leafref" {
					path "../source-intf-encap/intf-id";
				}
				description "The interface";
			}
			leaf "source-intf-encap__encap__outer__vid" {
				type "leafref" {
					path "../source-intf-encap/encap/outer/vid";
				}
				description "VLAN identifier (VID). Values greater than 4094 have special meaning.";
			}
			leaf "source-intf-encap__encap__outer__tpid" {
				type "leafref" {
					path "../source-intf-encap/encap/outer/tpid";
				}
				description "Tag protocol identifier (TPID)";
			}
			leaf "source-intf-encap__encap__outer__priority" {
				type "leafref" {
					path "../source-intf-encap/encap/outer/priority";
				}
				description "Priority code point (PCP)";
			}
			leaf "source-intf-encap__encap__inner__vid" {
				type "leafref" {
					path "../source-intf-encap/encap/inner/vid";
				}
				description "VLAN identifier (VID). Values greater than 4094 have special meaning.";
			}
			leaf "source-intf-encap__encap__inner__tpid" {
				type "leafref" {
					path "../source-intf-encap/encap/inner/tpid";
				}
				description "Tag protocol identifier (TPID)";
			}
			leaf "source-intf-encap__encap__inner__priority" {
				type "leafref" {
					path "../source-intf-encap/encap/inner/priority";
				}
				description "Priority code point (PCP)";
			}
			uses "intf-vlan-map-entry";
			description "Local forwarding of traffic coming from remote endpoints. The remote traffic is classified by the pseudowire interface and the tags received. The destination specifies the local interface and VLAN tag manipulation action.";
		}
		list "intf-vlan-to-pw-encap-tunnel-group-id-map" {
			key "intf-id encap__outer__vid encap__outer__tpid encap__outer__priority encap__inner__vid encap__inner__tpid encap__inner__priority";
			leaf "intf-id" {
				type "openconfig-interfaces:interface-id";
				description "The interface";
			}
			leaf "encap__outer__vid" {
				type "uint16";
				description "VLAN identifier (VID). Values greater than 4094 have special meaning.";
			}
			leaf "encap__outer__tpid" {
				type "arista-ebra-vlan-tpid:vlan-tpid";
				description "Tag protocol identifier (TPID)";
			}
			leaf "encap__outer__priority" {
				type "uint8";
				description "Priority code point (PCP)";
			}
			leaf "encap__inner__vid" {
				type "uint16";
				description "VLAN identifier (VID). Values greater than 4094 have special meaning.";
			}
			leaf "encap__inner__tpid" {
				type "arista-ebra-vlan-tpid:vlan-tpid";
				description "Tag protocol identifier (TPID)";
			}
			leaf "encap__inner__priority" {
				type "uint8";
				description "Priority code point (PCP)";
			}
			leaf "intf-vlan-to-pw-encap-tunnel-group-id-map-value" {
				type "pw-encap-tunnel-group-id";
				description "Represent the value of an element of intf-vlan-to-pw-encap-tunnel-group-id-map list.";
			}
			description "For local-remote patches, holding MPLS encapsulation information for matching (source) intf-vlan-encap";
		}
		list "pw-encap-tunnel-groups" {
			key "pw-encap-tunnel-group-id";
			uses "pw-encap-tunnel-group";
			description "List of pseudowire encap tunnel groups";
		}
		list "remote-connector-to-local-intf-map" {
			key "pw-intf-id";
			uses "remote-connector-to-local-intf";
			description "Map remote connector to local interfaces";
		}
		leaf "name" {
			type "string";
			description "name of the grouping";
		}
		description "Status of all Pseudowire patches";
	}
	augment "/arista-exp-eos:arista" {
		container "pseudowire" {
			container "status" {
				config "false";
				uses "status";
				description "status container";
			}
			description "pseudowire container";
		}
	}
}
