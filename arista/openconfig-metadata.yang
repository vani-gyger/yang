module "openconfig-metadata" {
	yang-version "1";
	namespace "http://openconfig.net/yang/openconfig-metadata";
	prefix "oc-metadata";
	import "openconfig-extensions" {
		prefix "oc-ext";
	}
	import "ietf-yang-metadata" {
		prefix "ietf-md";
	}
	organization "OpenConfig working group";
	contact "OpenConfig working group
	         www.openconfig.net";
	description "This module defines metadata types that are defined by
	             the OpenConfig group.";
	oc-ext:openconfig-version "0.1.0";
	revision "2020-08-06" {
		description "Initial revision.";
		reference "0.1.0";
	}
	ietf-md:annotation "protobuf-metadata" {
		type "binary" {
			length "0..1048000";
		}
		description "A binary marshalled protobuf message, with a size that does not exceed
		             1MiB containing metadata related to the element of the data tree at which
		             the metadata annotation is used.
		             
		             It is expected that this metadata can be both written and read by a
		             client - and that the value is persistent across system restarts.
		             
		             A client using this metadata extension should ensure that it is able
		             to unmarshal its contents successfully. It is suggested that the
		             payload should be a protobuf.Any message, which has corresponding
		             type information such that information as to the intended structure
		             can be retrieved by any reader.";
	}
}
