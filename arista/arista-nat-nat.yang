module "arista-nat-nat" {
	yang-version "1";
	namespace "http://arista.com/yang/experimental/eos/arista-nat-nat";
	prefix "arista-nat-nat";
	import "openconfig-extensions" {
		prefix "oc-ext";
	}
	import "arista-acl-spec" {
		prefix "arista-acl-spec";
	}
	import "arista-arnet-ip" {
		prefix "arista-arnet-ip";
	}
	import "arista-arnet-vrf-name" {
		prefix "arista-arnet-vrf-name";
	}
	import "arista-exp-eos" {
		prefix "arista-exp-eos";
	}
	import "openconfig-inet-types" {
		prefix "openconfig-inet-types";
	}
	import "openconfig-interfaces" {
		prefix "openconfig-interfaces";
	}
	import "openconfig-packet-match-types" {
		prefix "openconfig-packet-match-types";
	}
	organization "Arista Networks <http://arista.com/>";
	contact "Arista Networks <http://arista.com/>";
	description "Yang model for NAT.
	             
	             THIS YANG MODULE WAS GENERATED. DO NOT EDIT THIS FILE.";
	oc-ext:openconfig-version "1.0.0";
	revision "2022-03-28" {
		description "Version 1.0.0, generated on 2022-03-28";
		reference "1.0.0";
	}
	typedef "nat-target" {
		type "enumeration" {
			enum "SOURCE" {
				value "0";
				description "Translate the source of the connection.";
			}
			enum "DESTINATION" {
				value "1";
				description "Translate the destination of the connection.";
			}
		}
		description "Specify what part of the connection to translate.";
	}
	typedef "nat-table" {
		type "enumeration" {
			enum "DEFAULT_IMPL" {
				value "0";
				description "Translation is decided in ingress.";
			}
			enum "EGRESS" {
				value "1";
				description "Translation is decided in egress.";
			}
		}
		description "Specify when to translate the packet.";
	}
	grouping "static-key" {
		container "local-address" {
			uses "arista-arnet-ip:ip-and-port";
			description "IP and port of the local source connection.";
		}
		leaf "acl" {
			type "string";
			description "Name of the ACL specified within the static NAT configuration.";
		}
		leaf "table" {
			type "nat-table";
			description "Indicate if the translation happens in ingress (default) or egress.";
		}
		description "An identifier for a static NAT connection.";
	}
	grouping "dynamic-key" {
		leaf "acl" {
			type "string";
			description "Name of the ACL specified within the static NAT configuration.";
		}
		leaf "group" {
			type "uint16";
			description "When enabled, this identifier is used to match two twice dynamic NAT rules.";
		}
		description "An identifier for a dynamic NAT connection.";
	}
	grouping "dynamic-connection-flags" {
		leaf "target" {
			type "boolean";
			description "If set, the rule is used to translate the destination address of a packet, otherwise the source.";
		}
		leaf "full-cone" {
			type "boolean";
			description "If set, this connection is full-cone enabled.";
		}
		leaf "addr-only" {
			type "boolean";
			description "If set, all packet matching the address will be translated.";
		}
		leaf "twice-nat" {
			type "boolean";
			description "If set, both source and destination will be translated.";
		}
		leaf "established" {
			type "boolean";
			description "If set, it means that the connection is established.";
		}
		leaf "pkt-seen" {
			type "boolean";
			description "If set, it means that a packet for this connection has been seen by the forwarding plane.";
		}
		leaf "upnp-igd" {
			type "boolean";
			description "If set, this connection is set up by UPNP IGD.";
		}
		leaf "overload" {
			type "boolean";
			description "If set, this connection is using the interface address";
		}
		description "Defines specific attributes of a dynamic NAT connection.";
	}
	grouping "nat-static-connection" {
		container "static-key" {
			uses "static-key";
			description "Identifier of the connection.";
		}
		container "global-address" {
			uses "arista-arnet-ip:ip-and-port";
			description "New address and port of the connection.";
		}
		leaf "target" {
			type "nat-target";
			description "Specify what part of the connection to translate.";
		}
		leaf "protocol" {
			type "openconfig-packet-match-types:ip-protocol-type";
			description "IP Protocol used by the connection.";
		}
		leaf "vlan-id" {
			type "uint16";
			description "VLAN identifier.";
		}
		leaf "ingress" {
			type "boolean";
			description "If enabled, translation is decided in ingress.";
		}
		description "A NAT rule to always translate a specific connection.";
	}
	grouping "nat-twice-connection" {
		leaf "group" {
			type "uint16";
			description "Identifier used to match two twice NAT rules.";
		}
		container "src-ip-and-port-old" {
			uses "arista-arnet-ip:ip-and-port";
			description "Source Ip and Port before any translation.";
		}
		container "dst-ip-and-port-old" {
			uses "arista-arnet-ip:ip-and-port";
			description "Destination Ip and Port before any translation.";
		}
		container "src-ip-and-port-new" {
			uses "arista-arnet-ip:ip-and-port";
			description "Source Ip and Port after any translation.";
		}
		container "dst-ip-and-port-new" {
			uses "arista-arnet-ip:ip-and-port";
			description "Destination Ip and Port after any translation.";
		}
		leaf "protocol" {
			type "openconfig-packet-match-types:ip-protocol-type";
			description "IP Protocol used by the connection.";
		}
		leaf "vlan-id" {
			type "uint16";
			description "VLAN identifier.";
		}
		description "A NAT rule to always translate both source and destination of a specific connection.";
	}
	grouping "nat-trap-info" {
		leaf "vlan-id" {
			type "uint16";
			description "Trap on a specific VLAN identifier.";
		}
		leaf "trap-all" {
			type "boolean";
			description "If enabled, trap every connections.";
		}
		leaf "deny-all" {
			type "boolean";
			description "If enabled, deny every connections.";
		}
		leaf "full-cone" {
			type "boolean";
			description "If enabled, full cone will be set for each connection matched by this trap rule.";
		}
		leaf "addr-only" {
			type "boolean";
			description "If enabled, translations will only be done on addresses.";
		}
		leaf "priority" {
			type "uint32";
			description "Specify the priority of the trap rule.";
		}
		leaf "pool-id" {
			type "uint32";
			description "Indicate which pool of address will be used for translation.";
		}
		leaf "target" {
			type "nat-target";
			description "Specify what part of the connection to translate.";
		}
		container "twice-addr" {
			uses "arista-arnet-ip:ip-and-port";
			description "If twice NAT group is enabled, this states the new address of the connection.";
		}
		description "Specific information of a trap rule.";
	}
	grouping "nat-trap-filter" {
		leaf "seq-num" {
			type "uint32";
			description "Sequence number of the filter.";
		}
		leaf "source" {
			type "openconfig-inet-types:ipv4-prefix";
			description "IP Mask that matches on the source address.";
		}
		leaf "destination" {
			type "openconfig-inet-types:ipv4-prefix";
			description "IP Mask that matches on the destination address.";
		}
		leaf "reverse" {
			type "boolean";
			description "If enabled, this allows to trap packets from outside to inside network  for new connections.";
		}
		leaf "deny" {
			type "boolean";
			description "If enabled, drop connections specified within the filter.";
		}
		leaf "src-port" {
			type "uint16";
			description "Specify source port for FTP connection.";
		}
		leaf "dst-port" {
			type "uint16";
			description "Specify destination port for FTP connection.";
		}
		leaf "proto" {
			type "openconfig-packet-match-types:ip-protocol-type";
			description "Specify which IP protocol to filter.";
		}
		container "src-port-acl" {
			uses "arista-acl-spec:port-spec";
			description "Specify which source port to match.";
		}
		container "dst-port-acl" {
			uses "arista-acl-spec:port-spec";
			description "Specify which destination port to match.";
		}
		leaf "fwd-pkt" {
			type "boolean";
			description "Ignore";
		}
		description "Filter used by a dynamic trap rule to decide if a packet should be handled by the system.";
	}
	grouping "nat-dynamic-trap-rule" {
		container "key" {
			uses "dynamic-key";
			description "Identifier of the connection.";
		}
		container "trap-info" {
			uses "nat-trap-info";
			description "Specific information of a trap rule.";
		}
		list "trap-filter" {
			key "seq-num source destination reverse deny src-port dst-port proto src-port-acl__oper src-port-acl__ports dst-port-acl__oper dst-port-acl__ports fwd-pkt";
			leaf "seq-num" {
				type "uint32";
				description "Sequence number of the filter.";
			}
			leaf "source" {
				type "openconfig-inet-types:ipv4-prefix";
				description "IP Mask that matches on the source address.";
			}
			leaf "destination" {
				type "openconfig-inet-types:ipv4-prefix";
				description "IP Mask that matches on the destination address.";
			}
			leaf "reverse" {
				type "boolean";
				description "If enabled, this allows to trap packets from outside to inside network  for new connections.";
			}
			leaf "deny" {
				type "boolean";
				description "If enabled, drop connections specified within the filter.";
			}
			leaf "src-port" {
				type "uint16";
				description "Specify source port for FTP connection.";
			}
			leaf "dst-port" {
				type "uint16";
				description "Specify destination port for FTP connection.";
			}
			leaf "proto" {
				type "openconfig-packet-match-types:ip-protocol-type";
				description "Specify which IP protocol to filter.";
			}
			leaf "src-port-acl__oper" {
				type "arista-acl-spec:range-operator";
				description "Specify how to match the specified port.";
			}
			leaf "src-port-acl__ports" {
				type "string";
				description "Whitespace separated list of port to be used by the ACL.";
			}
			leaf "dst-port-acl__oper" {
				type "arista-acl-spec:range-operator";
				description "Specify how to match the specified port.";
			}
			leaf "dst-port-acl__ports" {
				type "string";
				description "Whitespace separated list of port to be used by the ACL.";
			}
			leaf "fwd-pkt" {
				type "boolean";
				description "Ignore";
			}
			leaf "trap-filter-value" {
				type "boolean";
				description "Represent the value of an element of trap-filter list.";
			}
			description "Filters coming from the ACL tied to the trap rule.";
		}
		leaf "name" {
			type "string";
			description "name of the grouping";
		}
		description "A NAT rule to trap and dynamically create NAT rules for new connections that matches a specific ACL.";
	}
	grouping "interface-status" {
		leaf "profile-or-interface-id" {
			type "openconfig-interfaces:interface-id";
			description "Identifier of a profile or an NAT interface.";
		}
		leaf "vrf-name" {
			type "arista-arnet-vrf-name:vrf-name";
			description "Name of the VRF associated to the profile or interface.";
		}
		list "nat-interface-list" {
			key "nat-interface-list-key";
			leaf "nat-interface-list-key" {
				type "openconfig-interfaces:interface-id";
				description "openconfig-interfaces:interface-id key for nat-interface-list list.";
			}
			leaf "nat-interface-list-value" {
				type "uint16";
				description "Represent the value of an element of nat-interface-list list.";
			}
			description "List of valid interfaces in the profile. Valid means the interface is nota member of a LAG, and the interface has a valid VLAN identifier.The list is keyed per VLAN identifier.";
		}
		list "static-connection" {
			key "static-key__local-address__ip static-key__local-address__port static-key__acl static-key__table";
			leaf "static-key__local-address__ip" {
				type "leafref" {
					path "../static-key/local-address/ip";
				}
				description "IPv4 address of the connection.";
			}
			leaf "static-key__local-address__port" {
				type "leafref" {
					path "../static-key/local-address/port";
				}
				description "Port of the connection.";
			}
			leaf "static-key__acl" {
				type "leafref" {
					path "../static-key/acl";
				}
				description "Name of the ACL specified within the static NAT configuration.";
			}
			leaf "static-key__table" {
				type "leafref" {
					path "../static-key/table";
				}
				description "Indicate if the translation happens in ingress (default) or egress.";
			}
			uses "nat-static-connection";
			description "List of static NAT connection handled by the system.";
		}
		list "twice-nat-connection" {
			key "group";
			uses "nat-twice-connection";
			description "List of twice NAT connection handled by the system.";
		}
		list "dynamic-trap-rule" {
			key "key__acl key__group";
			leaf "key__acl" {
				type "leafref" {
					path "../key/acl";
				}
				description "Name of the ACL specified within the static NAT configuration.";
			}
			leaf "key__group" {
				type "leafref" {
					path "../key/group";
				}
				description "When enabled, this identifier is used to match two twice dynamic NAT rules.";
			}
			uses "nat-dynamic-trap-rule";
			description "List of NAT trap rules handled by the system.";
		}
		leaf "name" {
			type "string";
			description "name of the grouping";
		}
		description "This contains the nat configuration for one (default) or more interfaces
		              (in profile mode).";
	}
	grouping "status" {
		list "interface-status" {
			key "profile-or-interface-id";
			uses "interface-status";
			description "Status of the NAT configuration within either a profile or an interface.";
		}
		leaf "name" {
			type "string";
			description "name of the grouping";
		}
		description "Status of NAT (Network Address Translation) configuration in the system.";
	}
	augment "/arista-exp-eos:arista" {
		container "ip" {
			container "nat" {
				container "status" {
					config "false";
					uses "status";
					description "status container";
				}
				description "nat container";
			}
			description "ip container";
		}
	}
}
