module "arista-sflow-deviations" {
	namespace "http://arista.com/yang/openconfig/sflow/deviations";
	prefix "arista-sflow-deviations";
	import "openconfig-sampling-sflow" {
		prefix "oc-sflow";
	}
	import "openconfig-extensions" {
		prefix "oc-ext";
	}
	import "openconfig-sampling" {
		prefix "oc-sampling";
	}
	organization "Arista Networks, Inc.";
	contact "Arista Networks, Inc.
	         Product Support";
	description "This module contains OpenConfig sFlow deviations in Arista EOS.
	             
	             Copyright (c) 2021 Arista Networks, Inc. All rights reserved.";
	oc-ext:openconfig-version "1.0.2";
	revision "2023-07-27" {
		description "Corrected egress-sampling-rate to ingress-sampling-rate";
		reference "1.0.3";
	}
	revision "2022-07-18" {
		description "Leaf sampling-rate was renamed to egress-sampling-rate";
		reference "1.0.2";
	}
	revision "2021-09-27" {
		description "pyang auto format";
		reference "1.0.1";
	}
	revision "2021-07-12" {
		description "Initial deviations file.";
		reference "1.0.0";
	}
	deviation "/oc-sampling:sampling/oc-sflow:sflow/oc-sflow:config/oc-sflow:ingress-sampling-rate" {
		description "Sampling rate has a default value of 1 << 20 in EOS";
		deviate "add" {
			default "1048576";
		}
	}
	deviation "/oc-sampling:sampling/oc-sflow:sflow/oc-sflow:state/oc-sflow:ingress-sampling-rate" {
		description "Sampling rate has a default value of 1 << 20 in EOS";
		deviate "add" {
			default "1048576";
		}
	}
}
