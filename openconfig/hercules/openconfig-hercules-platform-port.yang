submodule "openconfig-hercules-platform-port" {
	yang-version "1";
	belongs-to "openconfig-hercules-platform" {
		prefix "herc-platform";
	}
	import "openconfig-extensions" {
		prefix "oc-ext";
	}
	import "openconfig-platform" {
		prefix "oc-platform";
	}
	import "openconfig-if-ethernet" {
		prefix "oc-eth";
	}
	organization "OpenConfig Hercules Working Group";
	contact "openconfig-hercules@googlegroups.com";
	description "This submodule defines schema extensions to the
	             OpenConfig port model for the Hercules switch profile.";
	oc-ext:openconfig-version "0.2.0";
	revision "2018-06-01" {
		description "Initial version.";
		reference "0.2.0";
	}
	identity "SPEED_20GB" {
		base "oc-eth:ETHERNET_SPEED";
		description "20 GBps Ethernet";
	}
	grouping "hercules-port-config" {
		description "Configuration data for vendor-agnostic switch port
		             components";
		leaf "port-id" {
			type "uint32";
			description "A numeric identifier assigned by the SDN management
			             system for a physical port.  This is used for example
			             to create an association between the port and the node
			             that manages it.";
		}
	}
	grouping "hercules-port-state" {
		description "Operational state data for vendor-agnostic switch port
		             components";
	}
	augment "/oc-platform:components/oc-platform:component/oc-platform:port/oc-platform:config" {
		description "Configuration data for vendor-agnostic switch port components";
		uses "hercules-port-config";
	}
	augment "/oc-platform:components/oc-platform:component/oc-platform:port/oc-platform:state" {
		description "Operational state data for vendor-agnostic switch port components";
		uses "hercules-port-config";
		uses "hercules-port-state";
	}
}
