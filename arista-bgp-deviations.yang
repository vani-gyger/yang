module "arista-bgp-deviations" {
	namespace "http://arista.com/yang/openconfig/bgp/deviations";
	prefix "arista-bgp-deviations";
	import "openconfig-network-instance" {
		prefix "oc-netinst";
	}
	import "openconfig-policy-types" {
		prefix "oc-pol-types";
	}
	import "openconfig-extensions" {
		prefix "oc-ext";
	}
	organization "Arista Networks, Inc.";
	contact "Arista Networks, Inc.
	         Product Support";
	description "This module contains OpenConfig BGP deviations in Arista EOS.
	             
	             Copyright (c) 2016 Arista Networks, Inc. All rights reserved.";
	oc-ext:openconfig-version "1.27.1";
	revision "2024-06-03" {
		description "Revert removal of the default value of 1 for maximum-paths";
		reference "1.27.1";
	}
	revision "2024-05-07" {
		description "Remove default value for default-route advertisement configuration.";
		reference "1.27.0";
	}
	revision "2024-04-08" {
		description "Remove the default value of 1 for maximum-paths";
		reference "1.26.0";
	}
	revision "2024-03-25" {
		description "Remove default of BGP default-import-policy and default-export-policy on AFI-SAFI-specific peer paths";
		reference "1.26.1";
	}
	revision "2024-03-18" {
		description "Remove default of use-multiple-paths";
		reference "1.26.0";
	}
	revision "2024-03-14" {
		description "Fix policy leaf deviations pointing to incorrect location for afi-safi-name leaf.";
		reference "1.25.3";
	}
	revision "2024-03-07" {
		description "Remove use-multiple-paths deviation";
		reference "1.25.2";
	}
	revision "2024-01-25" {
		description "Fix policy leaf deviations that constrain the AFI-SAFIs for which policy can be configured.";
		reference "1.25.1";
	}
	revision "2024-01-10" {
		description "Add maximum items constraint for neighbors/peer-groups afi-safi-level import-policy and export-policy.";
		reference "1.25.0";
	}
	revision "2023-08-22" {
		description "Added support for RT-membership AF for BGP neighbors.";
		reference "1.24.0";
	}
	revision "2023-05-17" {
		description "Add L3VPN unicast AFI-SAFIs support for BGP neighbors";
		reference "1.23.0";
	}
	revision "2023-03-10" {
		description "ADD L3VPN unicast AFI-SAFIs support for BGP global";
		reference "1.22.0";
	}
	revision "2022-12-12" {
		description "Remove deviations for AFI-SAFI peer enabled flag.";
		reference "1.21.0";
	}
	revision "2022-12-12" {
		description "Add extra deviations for peer group name sharing across VRFs.";
		reference "1.20.0";
	}
	revision "2022-09-28" {
		description "Add EVPN AFI-SAFI support for BGP global.";
		reference "1.19.0";
	}
	revision "2022-08-22" {
		description "Add support for last error notification time and counter.";
		reference "1.18.0";
	}
	revision "2022-08-15" {
		description "Remove default of mtu-discovery.";
		reference "1.17.0";
	}
	revision "2022-07-06" {
		description "Remove default of extended-next-hop-encoding.";
		reference "1.16.0";
	}
	revision "2022-07-02" {
		description "Remove deviations for BGP AFI/SAFI prefix-limit prevent-teardown.";
		reference "1.15.0";
	}
	revision "2022-05-30" {
		description "Fix range restriction for minimum-advertisement-interval.";
		reference "1.14.0";
	}
	revision "2022-05-13" {
		description "EOS support a different range for neighbor restart-time.";
		reference "1.13.0";
	}
	revision "2022-05-12" {
		description "Transition decimal64 types to uint16 for various BGP timers";
		reference "1.12.0";
	}
	revision "2022-03-31" {
		description "Remove deviations for bgp neighor/state/active, as EOS spports it now.";
		reference "1.11.0";
	}
	revision "2022-03-10" {
		description "Remove deviations for restart-timer, since this is no longer in the model.";
		reference "1.10.0";
	}
	revision "2022-01-20" {
		description "Add support for multicast AFI_SAFIs.";
		reference "1.9.0";
	}
	revision "2022-01-19" {
		description "Remove supported-capabilities as not supported.";
		reference "1.8.0";
	}
	revision "2021-12-15" {
		description "Remove default of BGP add-paths send and limit send-max to 2-64";
		reference "1.7.0";
	}
	revision "2021-10-14" {
		description "Remove default of BGP default-import-policy and default-export-policy";
		reference "1.6.1";
	}
	revision "2021-10-04" {
		description "Added aggregates-addresses list support for multicast.";
		reference "1.6.0";
	}
	revision "2021-09-27" {
		description "fix pyang BAD_DEVIATE_ADD error";
		reference "1.5.1";
	}
	revision "2021-09-07" {
		description "Remove unsupported leaves for prefix-limits.";
		reference "1.5.0";
	}
	revision "2021-07-28" {
		description "Remove deviations for local-address.";
		reference "1.4.0";
	}
	revision "2021-04-21" {
		description "Add default values for administrative distances of BGP learned routes to match EOS defaults.";
		reference "1.3.0";
	}
	revision "2021-03-30" {
		description "Add maximum items constraint for neighbors/peer-groups export-policy.";
		reference "1.2.0";
	}
	revision "2020-12-08" {
		description "Add range restriction for minimum-advertisement-interval, fix range restriction for hold-time.";
		reference "1.1.2";
	}
	revision "2020-11-30" {
		description "Fix errors reported by pyang.";
		reference "1.1.1";
	}
	revision "2020-05-27" {
		description "Removed route-target import/export policy deviations.";
		reference "1.1.0";
	}
	revision "2020-01-07" {
		description "Fixed default value of minimum-advertisement-interval in deviate delete.";
		reference "1.0.3";
	}
	revision "2020-01-06" {
		description "Removed unused imports.";
		reference "1.0.2";
	}
	revision "2019-05-25" {
		description "Add prefixes to identity names in must statements.";
		reference "1.0.1";
	}
	revision "2016-02-01" {
		description "Initial deviations file.";
		reference "1.0.0";
	}
	augment "/oc-netinst:network-instances/oc-netinst:network-instance/oc-netinst:protocols/oc-netinst:protocol/oc-netinst:bgp/oc-netinst:global/oc-netinst:config/oc-netinst:as" {
		description "The AS number can only be set in the default network-instance";
	}
	augment "/oc-netinst:network-instances/oc-netinst:network-instance/oc-netinst:protocols/oc-netinst:protocol/oc-netinst:bgp/oc-netinst:neighbors/oc-netinst:neighbor/oc-netinst:ebgp-multihop/oc-netinst:config/oc-netinst:enabled" {
		description "enabled is not used by EOS. Set multihop-ttl to a non-zero value to enable ebgp-multihop";
	}
	augment "/oc-netinst:network-instances/oc-netinst:network-instance/oc-netinst:protocols/oc-netinst:protocol/oc-netinst:bgp/oc-netinst:peer-groups/oc-netinst:peer-group/oc-netinst:ebgp-multihop/oc-netinst:config/oc-netinst:enabled" {
		description "enabled is not used by EOS. Set multihop-ttl to a non-zero value to enable ebgp-multihop";
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:config/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:state/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:config/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:state/oc-netinst:send-default-route" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:config/oc-netinst:peer-type" {
		description "peer-type is not supported in EOS";
		deviate "not-supported";
	}
	deviation "/oc-netinst:network-instances/oc-netinst:network-instance/oc-netinst:protocols/oc-netinst:protocol/oc-netinst:bgp/oc-netinst:peer-groups/oc-netinst:peer-group/oc-netinst:config/oc-netinst:peer-type" {
		description "peer-type is not supported in EOS";
		deviate "not-supported";
	}
	deviation "/oc-netinst:network-instances/oc-netinst:network-instance/oc-netinst:protocols/oc-netinst:protocol/oc-netinst:bgp/oc-netinst:neighbors/oc-netinst:neighbor/oc-netinst:as-path-options/oc-netinst:config/oc-netinst:allow-own-as" {
		description "EOS value is a triState which is represented by the absence of the leaf so this leaf cannot have a default value";
		deviate "delete" {
			default "0";
		}
	}
	deviation "/oc-netinst:network-instances/oc-netinst:network-instance/oc-netinst:protocols/oc-netinst:protocol/oc-netinst:bgp/oc-netinst:neighbors/oc-netinst:neighbor/oc-netinst:as-path-options/oc-netinst:state/oc-netinst:allow-own-as" {
		description "EOS value is a triState which is represented by the absence of the leaf so this leaf cannot have a default value";
		deviate "delete" {
			default "0";
		}
	}
	deviation "/oc-netinst:network-instances/oc-netinst:network-instance/oc-netinst:protocols/oc-netinst:protocol/oc-netinst:bgp/oc-netinst:peer-groups/oc-netinst:peer-group/oc-netinst:as-path-options/oc-netinst:config/oc-netinst:allow-own-as" {
		description "EOS value is a triState which is represented by the absence of the leaf so this leaf cannot have a default value";
		deviate "delete" {
			default "0";
		}
	}
	deviation "/oc-netinst:network-instances/oc-netinst:network-instance/oc-netinst:protocols/oc-netinst:protocol/oc-netinst:bgp/oc-netinst:peer-groups/oc-netinst:peer-group/oc-netinst:as-path-options/oc-netinst:state/oc-netinst:allow-own-as" {
		description "EOS value is a triState which is represented by the absence of the leaf so this leaf cannot have a default value";
		deviate "delete" {
			default "0";
		}
	}
	deviation "/oc-netinst:network-instances/oc-netinst:network-instance/oc-netinst:protocols/oc-netinst:protocol/oc-netinst:bgp/oc-netinst:global/oc-netinst:use-multiple-paths/oc-netinst:ebgp/oc-netinst:config/oc-netinst:allow-multiple-as" {
		description "allow-multiple-as is not configurable in EOS";
		deviate "not-supported";
	}
	deviation "/oc-netinst:network-instances/oc-netinst:network-instance/oc-netinst:protocols/oc-netinst:protocol/oc-netinst:bgp/oc-netinst:global/oc-netinst:use-multiple-paths/oc-netinst:ebgp/oc-netinst:state/oc-netinst:allow-multiple-as" {
		description "allow-multiple-as is not configurable in EOS";
		deviate "not-supported";
	}
	deviation "/oc-netinst:network-instances/oc-netinst:network-instance/oc-netinst:protocols/oc-netinst:protocol/oc-netinst:bgp/oc-netinst:global/oc-netinst:route-selection-options/oc-netinst:config/oc-netinst:enable-aigp" {
		description "enable-aigp is not configurable in EOS";
		deviate "not-supported";
	}
	deviation "/oc-netinst:network-instances/oc-netinst:network-instance/oc-netinst:protocols/oc-netinst:protocol/oc-netinst:bgp/oc-netinst:global/oc-netinst:route-selection-options/oc-netinst:state/oc-netinst:enable-aigp" {
		description "enable-aigp is not configurable in EOS";
		deviate "not-supported";
	}
	deviation "/oc-netinst:network-instances/oc-netinst:network-instance/oc-netinst:protocols/oc-netinst:protocol/oc-netinst:bgp/oc-netinst:neighbors/oc-netinst:neighbor/oc-netinst:route-reflector/oc-netinst:config/oc-netinst:route-reflector-cluster-id" {
		description "EOS does not support per neighbor cluster-id configuration";
		deviate "not-supported";
	}
	deviation "/oc-netinst:network-instances/oc-netinst:network-instance/oc-netinst:protocols/oc-netinst:protocol/oc-netinst:bgp/oc-netinst:peer-groups/oc-netinst:peer-group/oc-netinst:route-reflector/oc-netinst:config/oc-netinst:route-reflector-cluster-id" {
		description "EOS does not support per peer-group cluster-id configuration";
		deviate "not-supported";
	}
	deviation "/oc-netinst:network-instances/oc-netinst:network-instance/oc-netinst:protocols/oc-netinst:protocol/oc-netinst:bgp/oc-netinst:neighbors/oc-netinst:neighbor/oc-netinst:timers/oc-netinst:config/oc-netinst:connect-retry" {
		description "connect-retry is not configurable in EOS";
		deviate "not-supported";
	}
	deviation "/oc-netinst:network-instances/oc-netinst:network-instance/oc-netinst:protocols/oc-netinst:protocol/oc-netinst:bgp/oc-netinst:neighbors/oc-netinst:neighbor/oc-netinst:timers/oc-netinst:state/oc-netinst:connect-retry" {
		description "connect-retry is not configurable in EOS";
		deviate "not-supported";
	}
	deviation "/oc-netinst:network-instances/oc-netinst:network-instance/oc-netinst:protocols/oc-netinst:protocol/oc-netinst:bgp/oc-netinst:neighbors/oc-netinst:neighbor/oc-netinst:timers/oc-netinst:config/oc-netinst:minimum-advertisement-interval" {
		description "EOS value is a triState which is represented by the absence of the leaf so this leaf cannot have a default value, also EOS value has a restrictive range.";
		deviate "replace" {
			type "uint16" {
				range "0..600";
			}
		}
		deviate "delete" {
			default "30";
		}
	}
	deviation "/oc-netinst:network-instances/oc-netinst:network-instance/oc-netinst:protocols/oc-netinst:protocol/oc-netinst:bgp/oc-netinst:neighbors/oc-netinst:neighbor/oc-netinst:timers/oc-netinst:state/oc-netinst:minimum-advertisement-interval" {
		description "EOS value is a triState which is represented by the absence of the leaf so this leaf cannot have a default value";
		deviate "delete" {
			default "30";
		}
	}
	deviation "/oc-netinst:network-instances/oc-netinst:network-instance/oc-netinst:protocols/oc-netinst:protocol/oc-netinst:bgp/oc-netinst:neighbors/oc-netinst:neighbor/oc-netinst:timers/oc-netinst:config/oc-netinst:restart-time" {
		description "EOS uses a different range.";
		deviate "replace" {
			type "uint32" {
				range "60..max";
			}
		}
	}
	deviation "/oc-netinst:network-instances/oc-netinst:network-instance/oc-netinst:protocols/oc-netinst:protocol/oc-netinst:bgp/oc-netinst:neighbors/oc-netinst:neighbor/oc-netinst:timers/oc-netinst:state/oc-netinst:restart-time" {
		description "EOS uses a different range.";
		deviate "replace" {
			type "uint32";
		}
	}
	deviation "/oc-netinst:network-instances/oc-netinst:network-instance/oc-netinst:protocols/oc-netinst:protocol/oc-netinst:bgp/oc-netinst:peer-groups/oc-netinst:peer-group/oc-netinst:timers/oc-netinst:config/oc-netinst:connect-retry" {
		description "connect-retry is not configurable in EOS";
		deviate "not-supported";
	}
	deviation "/oc-netinst:network-instances/oc-netinst:network-instance/oc-netinst:protocols/oc-netinst:protocol/oc-netinst:bgp/oc-netinst:peer-groups/oc-netinst:peer-group/oc-netinst:timers/oc-netinst:state/oc-netinst:connect-retry" {
		description "connect-retry is not configurable in EOS";
		deviate "not-supported";
	}
	deviation "/oc-netinst:network-instances/oc-netinst:network-instance/oc-netinst:protocols/oc-netinst:protocol/oc-netinst:bgp/oc-netinst:peer-groups/oc-netinst:peer-group/oc-netinst:timers/oc-netinst:config/oc-netinst:minimum-advertisement-interval" {
		description "EOS value is a triState which is represented by the absence of the leaf so this leaf cannot have a default value, also EOS value has a restrictive range.";
		deviate "replace" {
			type "uint16" {
				range "0..600";
			}
		}
		deviate "delete" {
			default "30";
		}
	}
	deviation "/oc-netinst:network-instances/oc-netinst:network-instance/oc-netinst:protocols/oc-netinst:protocol/oc-netinst:bgp/oc-netinst:peer-groups/oc-netinst:peer-group/oc-netinst:timers/oc-netinst:state/oc-netinst:minimum-advertisement-interval" {
		description "EOS value is a triState which is represented by the absence of the leaf so this leaf cannot have a default value";
		deviate "delete" {
			default "30";
		}
	}
	deviation "/oc-netinst:network-instances/oc-netinst:network-instance/oc-netinst:protocols/oc-netinst:protocol/oc-netinst:bgp/oc-netinst:peer-groups/oc-netinst:peer-group/oc-netinst:timers/oc-netinst:config/oc-netinst:restart-time" {
		description "EOS uses a different range.";
		deviate "replace" {
			type "uint32" {
				range "60..max";
			}
		}
	}
	deviation "/oc-netinst:network-instances/oc-netinst:network-instance/oc-netinst:protocols/oc-netinst:protocol/oc-netinst:bgp/oc-netinst:peer-groups/oc-netinst:peer-group/oc-netinst:timers/oc-netinst:state/oc-netinst:restart-time" {
		description "EOS uses a different range";
		deviate "replace" {
			type "uint32";
		}
	}
	deviation "/oc-netinst:network-instances/oc-netinst:network-instance/oc-netinst:protocols/oc-netinst:protocol/oc-netinst:bgp/oc-netinst:neighbors/oc-netinst:neighbor/oc-netinst:as-path-options/oc-netinst:config/oc-netinst:disable-peer-as-filter" {
		description "disable-peer-as-filter is not configurable in EOS";
		deviate "not-supported";
	}
	deviation "/oc-netinst:network-instances/oc-netinst:network-instance/oc-netinst:protocols/oc-netinst:protocol/oc-netinst:bgp/oc-netinst:neighbors/oc-netinst:neighbor/oc-netinst:as-path-options/oc-netinst:state/oc-netinst:disable-peer-as-filter" {
		description "disable-peer-as-filter is not configurable in EOS";
		deviate "not-supported";
	}
	deviation "/oc-netinst:network-instances/oc-netinst:network-instance/oc-netinst:protocols/oc-netinst:protocol/oc-netinst:bgp/oc-netinst:peer-groups/oc-netinst:peer-group/oc-netinst:as-path-options/oc-netinst:config/oc-netinst:disable-peer-as-filter" {
		description "disable-peer-as-filter is not configurable in EOS";
		deviate "not-supported";
	}
	deviation "/oc-netinst:network-instances/oc-netinst:network-instance/oc-netinst:protocols/oc-netinst:protocol/oc-netinst:bgp/oc-netinst:neighbors/oc-netinst:neighbor/oc-netinst:config/oc-netinst:route-flap-damping" {
		description "route-flap-damping is not configurable in EOS";
		deviate "not-supported";
	}
	deviation "/oc-netinst:network-instances/oc-netinst:network-instance/oc-netinst:protocols/oc-netinst:protocol/oc-netinst:bgp/oc-netinst:neighbors/oc-netinst:neighbor/oc-netinst:state/oc-netinst:route-flap-damping" {
		description "route-flap-damping is not configurable in EOS";
		deviate "not-supported";
	}
	deviation "/oc-netinst:network-instances/oc-netinst:network-instance/oc-netinst:protocols/oc-netinst:protocol/oc-netinst:bgp/oc-netinst:peer-groups/oc-netinst:peer-group/oc-netinst:as-path-options/oc-netinst:state/oc-netinst:disable-peer-as-filter" {
		description "disable-peer-as-filter is not configurable in EOS";
		deviate "not-supported";
	}
	deviation "/oc-netinst:network-instances/oc-netinst:network-instance/oc-netinst:protocols/oc-netinst:protocol/oc-netinst:bgp/oc-netinst:neighbors/oc-netinst:neighbor/oc-netinst:transport/oc-netinst:config/oc-netinst:mtu-discovery" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:transport/oc-netinst:config/oc-netinst:mtu-discovery" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:transport/oc-netinst:state/oc-netinst:mtu-discovery" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:transport/oc-netinst:state/oc-netinst:mtu-discovery" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:logging-options/oc-netinst:config/oc-netinst:log-neighbor-state-changes" {
		description "Neighbor state change logging cannot be configured for a neighbor in EOS";
		deviate "not-supported";
	}
	deviation "/oc-netinst:network-instances/oc-netinst:network-instance/oc-netinst:protocols/oc-netinst:protocol/oc-netinst:bgp/oc-netinst:neighbors/oc-netinst:neighbor/oc-netinst:logging-options/oc-netinst:state/oc-netinst:log-neighbor-state-changes" {
		description "Neighbor state change logging is not supported for a neighbor in EOS";
		deviate "delete" {
			default "true";
		}
	}
	deviation "/oc-netinst:network-instances/oc-netinst:network-instance/oc-netinst:protocols/oc-netinst:protocol/oc-netinst:bgp/oc-netinst:peer-groups/oc-netinst:peer-group/oc-netinst:logging-options/oc-netinst:config/oc-netinst:log-neighbor-state-changes" {
		description "Neighbor state change logging cannot be configured for a peer-group in EOS";
		deviate "not-supported";
	}
	deviation "/oc-netinst:network-instances/oc-netinst:network-instance/oc-netinst:protocols/oc-netinst:protocol/oc-netinst:bgp/oc-netinst:peer-groups/oc-netinst:peer-group/oc-netinst:logging-options/oc-netinst:state/oc-netinst:log-neighbor-state-changes" {
		description "Neighbor state change logging is not supported for a peer-group in EOS";
		deviate "delete" {
			default "true";
		}
	}
	deviation "/oc-netinst:network-instances/oc-netinst:network-instance/oc-netinst:protocols/oc-netinst:protocol/oc-netinst:bgp/oc-netinst:neighbors/oc-netinst:neighbor/oc-netinst:timers/oc-netinst:config/oc-netinst:hold-time" {
		description "EOS range restriction and default";
		deviate "replace" {
			type "uint16" {
				range "0 | 3..7200";
			}
		}
		deviate "delete" {
			default "90";
		}
	}
	deviation "/oc-netinst:network-instances/oc-netinst:network-instance/oc-netinst:protocols/oc-netinst:protocol/oc-netinst:bgp/oc-netinst:neighbors/oc-netinst:neighbor/oc-netinst:timers/oc-netinst:config/oc-netinst:keepalive-interval" {
		description "keepalive interval EOS range restriction and default";
		deviate "replace" {
			type "uint16" {
				range "0..3600";
			}
		}
		deviate "delete" {
			default "30";
		}
	}
	deviation "/oc-netinst:network-instances/oc-netinst:network-instance/oc-netinst:protocols/oc-netinst:protocol/oc-netinst:bgp/oc-netinst:neighbors/oc-netinst:neighbor/oc-netinst:timers/oc-netinst:state/oc-netinst:hold-time" {
		description "EOS value is a triState which is represented by the absence of the leaf so this leaf cannot have a default value";
		deviate "delete" {
			default "90";
		}
	}
	deviation "/oc-netinst:network-instances/oc-netinst:network-instance/oc-netinst:protocols/oc-netinst:protocol/oc-netinst:bgp/oc-netinst:neighbors/oc-netinst:neighbor/oc-netinst:timers/oc-netinst:state/oc-netinst:keepalive-interval" {
		description "EOS value is a triState which is represented by the absence of the leaf so this leaf cannot have a default value";
		deviate "delete" {
			default "30";
		}
	}
	deviation "/oc-netinst:network-instances/oc-netinst:network-instance/oc-netinst:protocols/oc-netinst:protocol/oc-netinst:bgp/oc-netinst:peer-groups/oc-netinst:peer-group/oc-netinst:timers/oc-netinst:config/oc-netinst:hold-time" {
		description "hold-time EOS range restriction and default";
		deviate "replace" {
			type "uint16" {
				range "0 | 3..7200";
			}
		}
		deviate "delete" {
			default "90";
		}
	}
	deviation "/oc-netinst:network-instances/oc-netinst:network-instance/oc-netinst:protocols/oc-netinst:protocol/oc-netinst:bgp/oc-netinst:global/oc-netinst:graceful-restart/oc-netinst:config/oc-netinst:restart-time" {
		description "restart-time EOS range restriction";
		deviate "replace" {
			type "uint16" {
				range "1..3600";
			}
		}
	}
	deviation "/oc-netinst:network-instances/oc-netinst:network-instance/oc-netinst:protocols/oc-netinst:protocol/oc-netinst:bgp/oc-netinst:global/oc-netinst:graceful-restart/oc-netinst:config/oc-netinst:stale-routes-time" {
		description "stale-routes-time EOS range restriction";
		deviate "replace" {
			type "uint16" {
				range "1..3600";
			}
		}
	}
	deviation "/oc-netinst:network-instances/oc-netinst:network-instance/oc-netinst:protocols/oc-netinst:protocol/oc-netinst:bgp/oc-netinst:peer-groups/oc-netinst:peer-group/oc-netinst:timers/oc-netinst:config/oc-netinst:keepalive-interval" {
		description "keepalive interval EOS range restriction and default";
		deviate "replace" {
			type "uint16" {
				range "0..3600";
			}
		}
		deviate "delete" {
			default "30";
		}
	}
	deviation "/oc-netinst:network-instances/oc-netinst:network-instance/oc-netinst:protocols/oc-netinst:protocol/oc-netinst:bgp/oc-netinst:peer-groups/oc-netinst:peer-group/oc-netinst:timers/oc-netinst:state/oc-netinst:hold-time" {
		description "EOS value is a triState which is represented by the absence of the leaf so this leaf cannot have a default value";
		deviate "delete" {
			default "90";
		}
	}
	deviation "/oc-netinst:network-instances/oc-netinst:network-instance/oc-netinst:protocols/oc-netinst:protocol/oc-netinst:bgp/oc-netinst:peer-groups/oc-netinst:peer-group/oc-netinst:timers/oc-netinst:state/oc-netinst:keepalive-interval" {
		description "EOS value is a triState which is represented by the absence of the leaf so this leaf cannot have a default value";
		deviate "delete" {
			default "30";
		}
	}
	deviation "/oc-netinst:network-instances/oc-netinst:network-instance/oc-netinst:protocols/oc-netinst:protocol/oc-netinst:bgp/oc-netinst:global/oc-netinst:route-selection-options/oc-netinst:config/oc-netinst:external-compare-router-id" {
		description "EOS value is a triStateBool which is represented by the absence of the leaf so this leaf can not have a default value";
		deviate "delete" {
			default "true";
		}
	}
	deviation "/oc-netinst:network-instances/oc-netinst:network-instance/oc-netinst:protocols/oc-netinst:protocol/oc-netinst:bgp/oc-netinst:global/oc-netinst:route-selection-options/oc-netinst:state/oc-netinst:external-compare-router-id" {
		description "EOS value is a triStateBool which is represented by the absence of the leaf so this leaf can not have a default value";
		deviate "delete" {
			default "true";
		}
	}
	deviation "/oc-netinst:network-instances/oc-netinst:network-instance/oc-netinst:protocols/oc-netinst:protocol/oc-netinst:bgp/oc-netinst:global/oc-netinst:route-selection-options/oc-netinst:config/oc-netinst:ignore-as-path-length" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:state/oc-netinst:ignore-as-path-length" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:config/oc-netinst:advertise-inactive-routes" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:state/oc-netinst:advertise-inactive-routes" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:config/oc-netinst:always-compare-med" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:state/oc-netinst:always-compare-med" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:config/oc-netinst:ignore-next-hop-igp-metric" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:route-selection-options/oc-netinst:state/oc-netinst:ignore-next-hop-igp-metric" {
		description "EOS value is a triStateBool which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:use-multiple-paths/oc-netinst:config/oc-netinst:enabled" {
		description "Disabling EOS multiple-paths is not supported, multiple-paths is always enabled in EOS";
		deviate "replace" {
			config "false";
		}
		deviate "replace" {
			default "true";
		}
	}
	deviation "/oc-netinst:network-instances/oc-netinst:network-instance/oc-netinst:protocols/oc-netinst:protocol/oc-netinst:bgp/oc-netinst:global/oc-netinst:use-multiple-paths/oc-netinst:state/oc-netinst:enabled" {
		description "Disabling EOS multiple-paths is not supported, multiple-paths is always enabled in EOS";
		deviate "replace" {
			default "true";
		}
	}
	deviation "/oc-netinst:network-instances/oc-netinst:network-instance/oc-netinst:protocols/oc-netinst:protocol/oc-netinst:bgp/oc-netinst:global/oc-netinst:use-multiple-paths/oc-netinst:ebgp/oc-netinst:config/oc-netinst:maximum-paths" {
		description "EOS's value has an invalid state which is represented by the absence of the leaf so this leaf cannot have a default value";
		deviate "delete" {
			default "1";
		}
	}
	deviation "/oc-netinst:network-instances/oc-netinst:network-instance/oc-netinst:protocols/oc-netinst:protocol/oc-netinst:bgp/oc-netinst:global/oc-netinst:use-multiple-paths/oc-netinst:ebgp/oc-netinst:state/oc-netinst:maximum-paths" {
		description "EOS's value has an invalid state which is represented by the absence of the leaf so this leaf cannot have a default value";
		deviate "delete" {
			default "1";
		}
	}
	deviation "/oc-netinst:network-instances/oc-netinst:network-instance/oc-netinst:protocols/oc-netinst:protocol/oc-netinst:bgp/oc-netinst:global/oc-netinst:afi-safis/oc-netinst:afi-safi/oc-netinst:config/oc-netinst:afi-safi-name" {
		description "L2VPN_EVPN, IPV4_UNICAST, IPV6_UNICAST, IPV4_MULTICAST, IPV6_MULTICAST, L3VPN_IPV4_UNICAST and L3VPN_IPV6_UNICAST are the only AFI-SAFIs type supported in EOS";
		deviate "add" {
			must "../afi-safi-name = 'IPV4_UNICAST' or ../afi-safi-name = 'IPV6_UNICAST' or ../afi-safi-name = 'IPV4_MULTICAST' or ../afi-safi-name = 'IPV6_MULTICAST' or ../afi-safi-name = 'L2VPN_EVPN' or ../afi-safi-name = 'L3VPN_IPV4_UNICAST' or ../afi-safi-name = 'L3VPN_IPV6_UNICAST'" {
				error-message "L2VPN_EVPN, IPV4_UNICAST, IPV6_UNICAST, IPV4_MULTICAST, IPV6_MULTICAST, L3VPN_IPV4_UNICAST and L3VPN_IPV6_UNICAST are the only AFI-SAFIs type supported in EOS";
			}
		}
	}
	deviation "/oc-netinst:network-instances/oc-netinst:network-instance/oc-netinst:protocols/oc-netinst:protocol/oc-netinst:bgp/oc-netinst:global/oc-netinst:use-multiple-paths/oc-netinst:ibgp/oc-netinst:config/oc-netinst:maximum-paths" {
		description "iBGP multiple-paths is not supported in EOS";
		deviate "not-supported";
	}
	deviation "/oc-netinst:network-instances/oc-netinst:network-instance/oc-netinst:protocols/oc-netinst:protocol/oc-netinst:bgp/oc-netinst:global/oc-netinst:afi-safis/oc-netinst:afi-safi/oc-netinst:config/oc-netinst:enabled" {
		description "EOS allows inheriting the value from a different configuration command which is represented by the absence of the leaf so this leaf can not have a default value";
		deviate "delete" {
			default "false";
		}
	}
	deviation "/oc-netinst:network-instances/oc-netinst:network-instance/oc-netinst:protocols/oc-netinst:protocol/oc-netinst:bgp/oc-netinst:global/oc-netinst:afi-safis/oc-netinst:afi-safi/oc-netinst:state/oc-netinst:enabled" {
		description "EOS allows inheriting the value from a different configuration command which is represented by the absence of the leaf so this leaf can not have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:config/oc-netinst:afi-safi-name" {
		description "L2VPN_EVPN,
		             IPV4_UNICAST, IPV6_UNICAST,
		             IPV4_MULTICAST, IPV6_MULTICAST,
		             L3VPN_IPV4_UNICAST, L3VPN_IPV6_UNICAST and
		             RT_MEMBERSHIP
		             are the only AFI-SAFIs type supported in EOS";
		deviate "add" {
			must "../afi-safi-name = 'IPV4_UNICAST' or ../afi-safi-name = 'IPV6_UNICAST' or ../afi-safi-name = 'L2VPN_EVPN' or ../afi-safi-name = 'IPV4_MULTICAST' or ../afi-safi-name = 'IPV6_MULTICAST' or ../afi-safi-name = 'L3VPN_IPV4_UNICAST' or ../afi-safi-name = 'L3VPN_IPV6_UNICAST' or ../afi-safi-name = 'RT_MEMBERSHIP'" {
				error-message "L2VPN_EVPN,
				               IPV4_UNICAST, IPV6_UNICAST,
				               IPV4_MULTICAST, IPV6_MULTICAST,
				               L3VPN_IPV4_UNICAST, L3VPN_IPV6_UNICAST and
				               RT_MEMBERSHIP
				               are the only AFI-SAFIs type supported in EOS";
			}
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:config/oc-netinst:afi-safi-name" {
		description "L2VPN_EVPN,
		             IPV4_UNICAST, IPV6_UNICAST,
		             IPV4_MULTICAST, IPV6_MULTICAST,
		             L3VPN_IPV4_UNICAST, L3VPN_IPV6_UNICAST and
		             RT_MEMBERSHIP
		             are the only AFI-SAFIs type supported in EOS";
		deviate "add" {
			must "../afi-safi-name = 'IPV4_UNICAST' or ../afi-safi-name = 'IPV6_UNICAST' or ../afi-safi-name = 'L2VPN_EVPN' or ../afi-safi-name = 'IPV4_MULTICAST' or ../afi-safi-name = 'IPV6_MULTICAST' or ../afi-safi-name = 'L3VPN_IPV4_UNICAST' or ../afi-safi-name = 'L3VPN_IPV6_UNICAST' or ../afi-safi-name = 'RT_MEMBERSHIP'" {
				error-message "L2VPN_EVPN,
				               IPV4_UNICAST, IPV6_UNICAST,
				               IPV4_MULTICAST, IPV6_MULTICAST,
				               L3VPN_IPV4_UNICAST, L3VPN_IPV6_UNICAST and
				               RT_MEMBERSHIP
				               are the only AFI-SAFIs type supported in EOS";
			}
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:use-multiple-paths" {
		description "Configuring multiple-paths per afi-safi for a neighbor is not supported in EOS";
		deviate "not-supported";
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:receive" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:receive" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:receive" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:receive" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:send" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:send" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:send" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:send" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:send-max" {
		description "EOS value is within the range of 2-64";
		deviate "replace" {
			type "uint8" {
				range "2..64";
			}
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:send-max" {
		description "EOS value is within the range of 2-64";
		deviate "replace" {
			type "uint8" {
				range "2..64";
			}
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:send-max" {
		description "EOS value is within the range of 2-64";
		deviate "replace" {
			type "uint8" {
				range "2..64";
			}
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:send-max" {
		description "EOS value is within the range of 2-64";
		deviate "replace" {
			type "uint8" {
				range "2..64";
			}
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:extended-next-hop-encoding" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:extended-next-hop-encoding" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:extended-next-hop-encoding" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:extended-next-hop-encoding" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:route-reflector/oc-netinst:config/oc-netinst:route-reflector-client" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:route-reflector/oc-netinst:state/oc-netinst:route-reflector-client" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:route-reflector/oc-netinst:config/oc-netinst:route-reflector-client" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:route-reflector/oc-netinst:state/oc-netinst:route-reflector-client" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:transport/oc-netinst:config/oc-netinst:passive-mode" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:transport/oc-netinst:state/oc-netinst:passive-mode" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:transport/oc-netinst:config/oc-netinst:passive-mode" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:transport/oc-netinst:state/oc-netinst:passive-mode" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:graceful-restart/oc-netinst:config/oc-netinst:enabled" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:graceful-restart/oc-netinst:state/oc-netinst:enabled" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:graceful-restart/oc-netinst:config/oc-netinst:enabled" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:graceful-restart/oc-netinst:state/oc-netinst:enabled" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:neighbors/oc-netinst:neighbor/oc-netinst:config/oc-netinst:peer-group" {
		description "In EOS, peer-groups are shared between network-instances and located in the default network-instance";
		deviate "replace" {
			type "string";
		}
		deviate "add" {
			must "../peer-group = /network-instances/network-instance[name='default']/protocols/protocol[name='BGP'][identifier='oc-pol-types:BGP']/bgp/peer-groups/peer-group/config/peer-group-name" {
				error-message "peer-groups should be shared with the default network-instance";
			}
		}
	}
	deviation "/oc-netinst:network-instances/oc-netinst:network-instance/oc-netinst:protocols/oc-netinst:protocol/oc-netinst:bgp/oc-netinst:neighbors/oc-netinst:neighbor/oc-netinst:state/oc-netinst:peer-group" {
		description "In EOS, peer-groups are shared between network-instances and located in the default network-instance";
		deviate "replace" {
			type "string";
		}
		deviate "add" {
			must "../peer-group = /network-instances/network-instance[name='default']/protocols/protocol[name='BGP'][identifier='oc-pol-types:BGP']/bgp/peer-groups/peer-group/peer-group-name" {
				error-message "peer-groups should be shared with the default network-instance";
			}
		}
	}
	deviation "/oc-netinst:network-instances/oc-netinst:network-instance/oc-netinst:protocols/oc-netinst:protocol/oc-netinst:bgp/oc-netinst:global/oc-netinst:dynamic-neighbor-prefixes/oc-netinst:dynamic-neighbor-prefix/oc-netinst:config/oc-netinst:peer-group" {
		description "In EOS, peer-groups are shared between network-instances and located in the default network-instance";
		deviate "replace" {
			type "string";
		}
		deviate "add" {
			must "../peer-group = /network-instances/network-instance[name='default']/protocols/protocol[name='BGP'][identifier='oc-pol-types:BGP']/bgp/peer-groups/peer-group/config/peer-group-name" {
				error-message "peer-groups should be shared with the default network-instance";
			}
		}
	}
	deviation "/oc-netinst:network-instances/oc-netinst:network-instance/oc-netinst:protocols/oc-netinst:protocol/oc-netinst:bgp/oc-netinst:global/oc-netinst:dynamic-neighbor-prefixes/oc-netinst:dynamic-neighbor-prefix/oc-netinst:state/oc-netinst:peer-group" {
		description "In EOS, peer-groups are shared between network-instances and located in the default network-instance";
		deviate "replace" {
			type "string";
		}
		deviate "add" {
			must "../peer-group = /network-instances/network-instance[name='default']/protocols/protocol[name='BGP'][identifier='oc-pol-types:BGP']/bgp/peer-groups/peer-group/config/peer-group-name" {
				error-message "peer-groups should be shared with the default network-instance";
			}
		}
	}
	deviation "/oc-netinst:network-instances/oc-netinst:network-instance/oc-netinst:protocols/oc-netinst:protocol/oc-netinst:bgp/oc-netinst:neighbors/oc-netinst:neighbor/oc-netinst:apply-policy/oc-netinst:config/oc-netinst:export-policy" {
		description "In EOS, only one outbound policy can be applied to per neighbor";
		deviate "add" {
			max-elements "1";
		}
	}
	deviation "/oc-netinst:network-instances/oc-netinst:network-instance/oc-netinst:protocols/oc-netinst:protocol/oc-netinst:bgp/oc-netinst:peer-groups/oc-netinst:peer-group/oc-netinst:apply-policy/oc-netinst:config/oc-netinst:export-policy" {
		description "In EOS, only one outbound policy can be applied to per peer-group";
		deviate "add" {
			max-elements "1";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:import-policy" {
		description "Policy on a neighbor can only be configured on the IPV4_UNICAST and IPV6_UNICAST AFI-SAFIs";
		deviate "add" {
			must "../../../config/afi-safi-name = 'IPV4_UNICAST' or ../../../config/afi-safi-name = 'IPV6_UNICAST'" {
				error-message "Policy on a neighbor can only be configured on the IPV4_UNICAST and IPV6_UNICAST AFI-SAFIs";
			}
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:export-policy" {
		description "Policy on a neighbor can only be configured on the IPV4_UNICAST and IPV6_UNICAST AFI-SAFIs";
		deviate "add" {
			must "../../../config/afi-safi-name = 'IPV4_UNICAST' or ../../../config/afi-safi-name = 'IPV6_UNICAST'" {
				error-message "Policy on a neighbor can only be configured on the IPV4_UNICAST and IPV6_UNICAST AFI-SAFIs";
			}
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:import-policy" {
		description "Policy on a neighbor can only be configured on the IPV4_UNICAST and IPV6_UNICAST AFI-SAFIs";
		deviate "add" {
			must "../../../config/afi-safi-name = 'IPV4_UNICAST' or ../../../config/afi-safi-name = 'IPV6_UNICAST'" {
				error-message "Policy on a peer-group can only be configured on the IPV4_UNICAST and IPV6_UNICAST AFI-SAFIs";
			}
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:export-policy" {
		description "Policy on a neighbor can only be configured on the IPV4_UNICAST and IPV6_UNICAST AFI-SAFIs";
		deviate "add" {
			must "../../../config/afi-safi-name = 'IPV4_UNICAST' or ../../../config/afi-safi-name = 'IPV6_UNICAST'" {
				error-message "Policy on a peer-group can only be configured on the IPV4_UNICAST and IPV6_UNICAST AFI-SAFIs";
			}
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:import-policy" {
		description "In EOS, only one inbound policy can be applied per neighbor";
		deviate "add" {
			max-elements "1";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:import-policy" {
		description "In EOS, only one inbound policy can be applied per peer-group";
		deviate "add" {
			max-elements "1";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:export-policy" {
		description "In EOS, only one outbound policy can be applied per neighbor";
		deviate "add" {
			max-elements "1";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:export-policy" {
		description "In EOS, only one outbound policy can be applied per peer-group";
		deviate "add" {
			max-elements "1";
		}
	}
	deviation "/oc-netinst:network-instances/oc-netinst:network-instance/oc-netinst:protocols/oc-netinst:protocol/oc-netinst:bgp/oc-netinst:neighbors/oc-netinst:neighbor/oc-netinst:apply-policy/oc-netinst:config/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:apply-policy/oc-netinst:config/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:apply-policy/oc-netinst:config/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:apply-policy/oc-netinst:config/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:apply-policy/oc-netinst:state/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:apply-policy/oc-netinst:state/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:apply-policy/oc-netinst:state/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:apply-policy/oc-netinst:state/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:default-import-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:default-export-policy" {
		description "The default value is removed to allow the attribute to not be present. When this attribute is not present, its effective value is retrieved from another configuration/leaf.";
		deviate "delete" {
			default "REJECT_ROUTE";
		}
	}
	deviation "/oc-netinst:network-instances/oc-netinst:network-instance/oc-netinst:protocols/oc-netinst:protocol/oc-netinst:bgp/oc-netinst:global/oc-netinst:default-route-distance/oc-netinst:config/oc-netinst:internal-route-distance" {
		description "In EOS, the default administrative distance for BGP learned routes is 200";
		deviate "add" {
			default "200";
		}
	}
	deviation "/oc-netinst:network-instances/oc-netinst:network-instance/oc-netinst:protocols/oc-netinst:protocol/oc-netinst:bgp/oc-netinst:global/oc-netinst:default-route-distance/oc-netinst:config/oc-netinst:external-route-distance" {
		description "In EOS, the default administrative distance for BGP learned routes is 200";
		deviate "add" {
			default "200";
		}
	}
	deviation "/oc-netinst:network-instances/oc-netinst:network-instance/oc-netinst:protocols/oc-netinst:protocol/oc-netinst:bgp/oc-netinst:global/oc-netinst:default-route-distance/oc-netinst:state/oc-netinst:internal-route-distance" {
		description "In EOS, the default administrative distance for BGP learned routes is 200";
		deviate "add" {
			default "200";
		}
	}
	deviation "/oc-netinst:network-instances/oc-netinst:network-instance/oc-netinst:protocols/oc-netinst:protocol/oc-netinst:bgp/oc-netinst:global/oc-netinst:default-route-distance/oc-netinst:state/oc-netinst:external-route-distance" {
		description "In EOS, the default administrative distance for BGP learned routes is 200";
		deviate "add" {
			default "200";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:config/oc-netinst:enabled" {
		description "EOS value is a triState which is represented by the absence of the leaf so this leaf cannot have a default value";
		deviate "delete" {
			default "false";
		}
	}
	deviation "/oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:state/oc-netinst:enabled" {
		description "EOS value is a triState which is represented by the absence of the leaf so this leaf cannot have a default value";
		deviate "delete" {
			default "false";
		}
	}
}
